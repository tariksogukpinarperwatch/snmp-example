-- **********************************************************************
--
-- Product:             3Com LinkBuilder FMS
-- MIB Version:         2.00A
-- Comments:            The MIB is used in conjunction with version 2.00 of
--                      the FMS agent software, which supports all FMS, FMS II
--                      and 10BT/BTi units. This release is hosted on a 3C16030
--                      FMS Management Module.
--
-- History:             Date                    Reason for Change
--                      4th October 1993        Created from 1.30 MIB.
--                                              PDDRM Monitor Port Table now
--                                              supports per-port control of
--                                              link-state and partition traps.
--			11th November 1993	Created from 1.40 MIB.
--						Added support Resilience.
--						Added support for FMS II Units.
--						Added support for Modular Bridge.
--						Added SMART MIB Objects.
--
-- **********************************************************************
--	Copyright 3Com Technologies Limited. (1991) (1992) (1993)
-- **********************************************************************



-- --------------------------------------------------------------------
-- ************ THE STARTING POINT FOR ALL MIB DEFINITIONS ************
-- --------------------------------------------------------------------

          LBHUB-FMS-MIB DEFINITIONS ::= BEGIN

          IMPORTS
                  mgmt, NetworkAddress, IpAddress, Counter, Gauge,
                          TimeTicks, enterprises
                      FROM RFC1155-SMI
                  OBJECT-TYPE
		      FROM RFC-1212
		  TRAP-TYPE
		      FROM RFC-1215
		rpMauMediaAvailable, rptrPortAutoPartitionState
			FROM MAU-MIB
		  DisplayString, PhysAddress
		      FROM RFC1213-MIB;

          --  This MIB module uses the extended OBJECT-TYPE macro as
          --  defined in RFC 1212;

          --  MIB-II (same prefix as MIB-I)

          mib-2      OBJECT IDENTIFIER ::= { mgmt 1 }

          -- textual conventions

          DisplayString ::= OCTET STRING
          -- This data type is used to model textual information taken
          -- from the NVT ASCII character set.  By convention, objects
          -- with this syntax are declared as having
          --
          --      SIZE (0..255)

          PhysAddress ::= OCTET STRING
          -- This data type is used to model media addresses.  For many
          -- types of media, this will be in a binary representation.
          -- For example, an ethernet address would be represented as
          -- a string of 6 octets.

          -- groups in MIB-II

          system       OBJECT IDENTIFIER ::= { mib-2 1 }
          interfaces   OBJECT IDENTIFIER ::= { mib-2 2 }
          at           OBJECT IDENTIFIER ::= { mib-2 3 }
          ip           OBJECT IDENTIFIER ::= { mib-2 4 }
          icmp         OBJECT IDENTIFIER ::= { mib-2 5 }
          tcp          OBJECT IDENTIFIER ::= { mib-2 6 }
          udp          OBJECT IDENTIFIER ::= { mib-2 7 }
          egp          OBJECT IDENTIFIER ::= { mib-2 8 }

          -- historical (some say hysterical)
          -- cmot      OBJECT IDENTIFIER ::= { mib-2 9 }
          transmission OBJECT IDENTIFIER ::= { mib-2 10 }
          snmp         OBJECT IDENTIFIER ::= { mib-2 11 }

          dot1dBridge  OBJECT IDENTIFIER ::= { mib-2 17 }



-- --------------------------------------------------------------------
-- ******************* PRIVATE BRANCH FOR 3Com ************************
-- --------------------------------------------------------------------

-- private		OBJECT IDENTIFIER ::= { internet 4 }
-- enterprises	OBJECT IDENTIFIER ::= { private 1 }

a3Com		OBJECT IDENTIFIER ::= { enterprises 43 }

products	OBJECT IDENTIFIER ::= { a3Com 1 }

	terminalServer		OBJECT IDENTIFIER ::= { products 1 }
	dedicatedBridgeServer	OBJECT IDENTIFIER ::= { products 2 }
	dedicatedRouteServer	OBJECT IDENTIFIER ::= { products 3 }
	brouter			OBJECT IDENTIFIER ::= { products 4 }
	genericMSWorkstation	OBJECT IDENTIFIER ::= { products 5 }
	genericMSServer		OBJECT IDENTIFIER ::= { products 6 }
	genericUnixServer	OBJECT IDENTIFIER ::= { products 7 }
	hub			OBJECT IDENTIFIER ::= { products 8 }
	cards			OBJECT IDENTIFIER ::= { products 9 }
	chipsets		OBJECT IDENTIFIER ::= { products 10 }

		linkBuilder3GH		OBJECT IDENTIFIER ::= { hub 1 }
		linkBuilder10BTi	OBJECT IDENTIFIER ::= { hub 2 }
		linkBuilderECS		OBJECT IDENTIFIER ::= { hub 3 }
		linkBuilderMSH		OBJECT IDENTIFIER ::= { hub 4 }
		linkBuilderFMS		OBJECT IDENTIFIER ::= { hub 5 }
		linkBuilderFDDIwg	OBJECT IDENTIFIER ::= { hub 6 }
		linkBuilderFMSII	OBJECT IDENTIFIER ::= { hub 7 }
		linkSwitchFMS		OBJECT IDENTIFIER ::= { hub 8 }
		linkSwitchMSH		OBJECT IDENTIFIER ::= { hub 9 }
		linkBuilderFMSLBridge	OBJECT IDENTIFIER ::= { hub 10 }

		linkBuilder3GH-cards	OBJECT IDENTIFIER ::= { cards 1 }
		linkBuilder10BTi-cards	OBJECT IDENTIFIER ::= { cards 2 }
		linkBuilderECS-cards	OBJECT IDENTIFIER ::= { cards 3 }
		linkBuilderMSH-cards	OBJECT IDENTIFIER ::= { cards 4 }
		linkBuilderFMS-cards	OBJECT IDENTIFIER ::= { cards 5 }
		linkBuilderFMSII-cards	OBJECT IDENTIFIER ::= { cards 6 }

			linkBuilder10BTi-cards-utp	OBJECT IDENTIFIER ::= { linkBuilder10BTi-cards 1 }
			linkBuilder10BT-cards-utp	OBJECT IDENTIFIER ::= { linkBuilder10BTi-cards 2 }

			linkBuilderFMS-cards-utp	OBJECT IDENTIFIER ::= { linkBuilderFMS-cards 1 }
			linkBuilderFMS-cards-coax	OBJECT IDENTIFIER ::= { linkBuilderFMS-cards 2 }
			linkBuilderFMS-cards-fiber	OBJECT IDENTIFIER ::= { linkBuilderFMS-cards 3 }
			linkBuilderFMS-cards-12fiber	OBJECT IDENTIFIER ::= { linkBuilderFMS-cards 4 }
			linkBuilderFMS-cards-24utp	OBJECT IDENTIFIER ::= { linkBuilderFMS-cards 5 }

			linkBuilderFMSII-cards-12tp-rj45	OBJECT IDENTIFIER ::= { linkBuilderFMSII-cards 1 }
			linkBuilderFMSII-cards-10coax-bnc	OBJECT IDENTIFIER ::= { linkBuilderFMSII-cards 2 }
			linkBuilderFMSII-cards-6fiber-st	OBJECT IDENTIFIER ::= { linkBuilderFMSII-cards 3 }
			linkBuilderFMSII-cards-12fiber-st	OBJECT IDENTIFIER ::= { linkBuilderFMSII-cards 4 }
			linkBuilderFMSII-cards-24tp-rj45	OBJECT IDENTIFIER ::= { linkBuilderFMSII-cards 5 }
			linkBuilderFMSII-cards-24tp-telco	OBJECT IDENTIFIER ::= { linkBuilderFMSII-cards 6 }

--experimental		OBJECT IDENTIFIER ::= { a3Com 2 }
amp-mib			OBJECT IDENTIFIER ::= { a3Com 3 }
genericTrap		OBJECT IDENTIFIER ::= { a3Com 4 }
viewBuilderApps		OBJECT IDENTIFIER ::= { a3Com 5 }
specificTrap		OBJECT IDENTIFIER ::= { a3Com 6 }
linkBuilder3GH-mib	OBJECT IDENTIFIER ::= { a3Com 7 }
linkBuilder10BTi-mib 	OBJECT IDENTIFIER ::= { a3Com 8 }
linkBuilderECS-mib	OBJECT IDENTIFIER ::= { a3Com 9 }
generic			OBJECT IDENTIFIER ::= { a3Com 10 }

        genExperimental 	OBJECT IDENTIFIER ::= { generic 1 }
	setup			OBJECT IDENTIFIER ::= { generic 2 }
	sysLoader		OBJECT IDENTIFIER ::= { generic 3 }
	security		OBJECT IDENTIFIER ::= { generic 4 }
	gauges			OBJECT IDENTIFIER ::= { generic 5 }
	asciiAgent		OBJECT IDENTIFIER ::= { generic 6 }
	serialIf		OBJECT IDENTIFIER ::= { generic 7 }
	repeaterMgmt		OBJECT IDENTIFIER ::= { generic 8 }
	endStation		OBJECT IDENTIFIER ::= { generic 9 }
	localSnmp		OBJECT IDENTIFIER ::= { generic 10 }
	manager			OBJECT IDENTIFIER ::= { generic 11 }
	unusedGeneric12		OBJECT IDENTIFIER ::= { generic 12 }
	chassis			OBJECT IDENTIFIER ::= { generic 14 }
	mrmResilience		OBJECT IDENTIFIER ::= { generic 15 }
	tokenRing		OBJECT IDENTIFIER ::= { generic 16 }
	multiRepeater 		OBJECT IDENTIFIER ::= { generic 17 }
	bridgeMgmt		OBJECT IDENTIFIER ::= { generic 18 }
	fault			OBJECT IDENTIFIER ::= { generic 19 }
	poll			OBJECT IDENTIFIER ::= { generic 20 }
	powerSupply		OBJECT IDENTIFIER ::= { generic 21 }

		testData	OBJECT IDENTIFIER ::= { genExperimental 1 }
		ifExtensions	OBJECT IDENTIFIER ::= { genExperimental 2 }

netBuilder-mib			OBJECT IDENTIFIER ::= { a3Com 11 }
lBridgeECS-mib			OBJECT IDENTIFIER ::= { a3Com 12 }
deskMan-mib			OBJECT IDENTIFIER ::= { a3Com 13 }
linkBuilderMSH-mib		OBJECT IDENTIFIER ::= { a3Com 14 }
linkBuilderFMS-mib		OBJECT IDENTIFIER ::= { a3Com 15 }
linkBuilderFDDI-wghub-mib	OBJECT IDENTIFIER ::= { a3Com 16 }
linkSwitch-mib			OBJECT IDENTIFIER ::= { a3Com 17 }

------------------------------------------------------------------------------------------
--											--
--				Start of FMS Specific MIB				--
--											--
------------------------------------------------------------------------------------------

linkbuilderMonitorPackage	OBJECT IDENTIFIER ::= { linkBuilder10BTi-mib 1 }
linkbuilderConfigPackage	OBJECT IDENTIFIER ::= { linkBuilder10BTi-mib 2 }
linkbuilderStatusPackage	OBJECT IDENTIFIER ::= { linkBuilder10BTi-mib 3 }
--
-- { linkBuilder10BTi-mib 4 } and { linkBuilder10BTi-mib 5 are allocated elsewhere }
--
linkbuilderMonitorMacPackage	OBJECT IDENTIFIER ::= { linkBuilder10BTi-mib 6 }

vmMonBatteryStatus	OBJECT-TYPE
			SYNTAX			INTEGER {
							normal	(1),
							low	(2)
							}
			ACCESS			read-only
			STATUS			mandatory
			DESCRIPTION
			"The results of the start up check on NVRAM Battery condition."
			::= {linkbuilderMonitorPackage 1}

vmMonPOSTResults        OBJECT-TYPE
        		SYNTAX  INTEGER
        		ACCESS  read-only
        		STATUS  mandatory
        		DESCRIPTION
                	"The results of the Power On Self Test are recorded here.
			 The value read is a bit mask of possible errors, these
			 are as follows:-

			 bit  3 set - error accessing the Ethernet Address PROM
			 bit  5 set - error accessing System RAM
			 bit  6 set - error accessing NVRAM
			 bit  7 set - battery level low
			 bit  8 set - MFP errors
			 bit  9 set - LANCE errors
			 bit 11 set - error allocating unit ids to units
			 bit 12 set - error on acessing repeater
			 bit 13 set - as above
			 bit 14 set - as above
			 bit 15 set - as above
			 bit 16 set - as above
			 bit 17 set - error accessing processor bus

			 bit  2 set - error accessing the Ethernet Address PROM
			 bit  3 set - error accessing System RAM
			 bit  4 set - as above
			 bit  5 set - error accessing NVRAM
			 bit  6 set - battery level low
			 bit  7 set - MFP errors
			 bit  8 set - LANCE errors
			 bit  9 set - MBGA errors
			 bit 10 set - watchdog
			 bit 11 set - error allocating unit ids
			 bit 12 set - error on acessing repeater
			 bit 13 set - as above
			 bit 14 set - as above
			 bit 15 set - as above
			 bit 16 set - as above
			 bit 17 set - as above
			 bit 18 set - hardware bus error
			 bit 19 set - as above
			 bit 20 set - as above
			 bit 21 set - as above
			 bit 22 set - interrupt error
			 bit 23 set - as above
			 bit 24 set - unknown
			"
        		::= {linkbuilderMonitorPackage 2}

-- -----------------------------------------------------------------------------------------
-- Fault Log
--
-- The whole of a3Com(43).linkbuilder10BTi-mib(8).linkbuilderMonitorPackage(1).vmMonFault(3)
-- has been deprecated.  It is currently still implemented for backwards compatability.
-- All new applications should use a3Com(43).generic(10).fault(19) instead.
-- -----------------------------------------------------------------------------------------

vmMonFault		OBJECT IDENTIFIER ::= { linkbuilderMonitorPackage 3 }

vmMonFaultModifiedFlag	OBJECT-TYPE
			SYNTAX			INTEGER
							{
							clean-read	(1),
							modified	(2)
							}
			ACCESS			read-write
			STATUS			deprecated
			DESCRIPTION
				"In order to ensure a clean read of the Fault table this flag
				should be set to clean_read when commencing to read the table and should
				be examined after reading the entire table. If still set to clean_read
				then the table read is okay, if not the table should be
				re-read as it has been modified during the read process."
			::= { vmMonFault 1 }

vmMonFaultTable		OBJECT-TYPE
			SYNTAX	SEQUENCE OF 	VmMonFaultEntry
			ACCESS			not-accessible
			STATUS			deprecated
			DESCRIPTION
				"The Fault Table."
			::= { vmMonFault 2 }

vmMonFaultEntry		OBJECT-TYPE
			SYNTAX			VmMonFaultEntry
			ACCESS			not-accessible
			STATUS			deprecated
			DESCRIPTION
				"Information relating to a single fault."
			INDEX			{ vmMonFaultIndex }
			::= { vmMonFaultTable 1 }

			VmMonFaultEntry ::= SEQUENCE {
						vmMonFaultIndex		INTEGER,
						vmMonFaultErrorNumber	INTEGER,
						vmMonFaultTimeStamp	TimeTicks,
						vmMonFaultRestartCount	INTEGER
						     }

vmMonFaultIndex		OBJECT-TYPE
			SYNTAX			INTEGER
			ACCESS			read-only
			STATUS			deprecated
			DESCRIPTION
				"The index into the Fault table.  The initial read from the
				table should be read as the next, from an index of 0;
				subsequent reads should read the next from the index returned
				by the previous read."
			::= { vmMonFaultEntry 1 }

vmMonFaultErrorNumber	OBJECT-TYPE
			SYNTAX			INTEGER
			ACCESS			read-only
			STATUS			deprecated
			DESCRIPTION
				"This error number for this fault log entry."
			::= { vmMonFaultEntry 2 }

vmMonFaultTimeStamp	OBJECT-TYPE
			SYNTAX			TimeTicks
			ACCESS			read-only
			STATUS			deprecated
			DESCRIPTION
				"The time since startup, in milliseconds, when the fault
				occurred."
			::= { vmMonFaultEntry 3 }

vmMonFaultRestartCount	OBJECT-TYPE
			SYNTAX			INTEGER
			ACCESS			read-only
			STATUS			deprecated
			DESCRIPTION
				"The number of restarts at time of fault."
			::= { vmMonFaultEntry 4 }

-- -----------------------------------------------------------------------------------------
-- The following MIB objects have been dprecated:
-- a3Com(43).linkbuilder10BTi-mib(8).linkbuilderMonitorPackage(1).vmMonDvtEcho(4)
-- a3Com(43).linkbuilder10BTi-mib(8).linkbuilderMonitorPackage(1).vmMonMgmtBusOverrunError(5)
-- a3Com(43).linkbuilder10BTi-mib(8).linkbuilderMonitorPackage(1).vmMonMgmtBusFramingError(6)
-- a3Com(43).linkbuilder10BTi-mib(8).linkbuilderMonitorPackage(1).vmMonMgmtBusOverflowError(7)
-- a3Com(43).linkbuilder10BTi-mib(8).linkbuilderMonitorPackage(1).vmMonMgmtBusFiFoFullCounter(8)
-- -----------------------------------------------------------------------------------------

vmMonDvtEcho	        OBJECT-TYPE
        		SYNTAX  INTEGER {
                			disabled (1),
                			enabled  (2)
                			}
        		ACCESS  write-only
        		STATUS  deprecated
        		DESCRIPTION
                	"This enables/disables the Echo service for test purposes only."
        		::= {linkbuilderMonitorPackage 4}

vmMonMgmtBusOverrunError        OBJECT-TYPE
			SYNTAX	Counter
        		ACCESS  read-only
        		STATUS  deprecated
        		DESCRIPTION
                	"Hardware error counter."
        		::= {linkbuilderMonitorPackage 5}

vmMonMgmtBusFramingError        OBJECT-TYPE
			SYNTAX	Counter
        		ACCESS  read-only
        		STATUS  deprecated
        		DESCRIPTION
                	"Hardware error counter."
        		::= {linkbuilderMonitorPackage 6}

vmMonMgmtBusOverflowError        OBJECT-TYPE
			SYNTAX	Counter
        		ACCESS  read-only
        		STATUS  deprecated
        		DESCRIPTION
                	"Hardware error counter."
        		::= {linkbuilderMonitorPackage 7}

vmMonMgmtBusFiFoFullCounter        OBJECT-TYPE
			SYNTAX	Counter
        		ACCESS  read-only
        		STATUS  deprecated
        		DESCRIPTION
                	"Hardware error counter."
        		::= {linkbuilderMonitorPackage 8}

-- -----------------------------------------------------------------------------------------
--
--	FMS Config Group Table
--
--	The whole of the vmConfigGroupTable has been deprecated.
--	It is currently still implemented for backwards compatability,
--	but all new applications should use the equivelant objects in the mrmCardTable.
--
--------------------------------------------------------------------------------------------

vmConfigGroupTable	OBJECT-TYPE
			SYNTAX			SEQUENCE OF VmConfigGroupEntry
			ACCESS			not-accessible
			STATUS			deprecated
			DESCRIPTION
			"Table configuration options for all of the groups."
			::= {linkbuilderConfigPackage 2}

vmConfigGroupEntry	OBJECT-TYPE
			SYNTAX			VmConfigGroupEntry
			ACCESS			not-accessible
			STATUS			deprecated
			DESCRIPTION
			"Configuration options for a single group."
			INDEX			{vmConGroupIndex}
			::= {vmConfigGroupTable 1}

			VmConfigGroupEntry ::= SEQUENCE {
						vmConGroupIndex				INTEGER,
						vmConGroupPortMask			INTEGER
			}

vmConGroupIndex		OBJECT-TYPE
			SYNTAX			INTEGER (1..16)
			ACCESS			read-only
			STATUS			deprecated
			DESCRIPTION
			"This attribute uniquely identifies this group within the repeater, it is
			part of the index for the group table."
			::= {vmConfigGroupEntry 1}

vmConGroupPortMask	OBJECT-TYPE
			SYNTAX			INTEGER
			ACCESS			read-only
			STATUS			deprecated
			DESCRIPTION
			"This attribute identifies which ports are present on this group. It is
			formatted as a bit mask. Bit 0, the least significant bit, represents
			port number one, bit 1 represents port number two and so on. Port number
			one is the port that has a xxxxPortIndex of 1 where xxxx depends upon which
			MIB table is being examined. The bits in the bit mask are set to a 1 if the
			port is present in this group and set to a zero if the port is not present."
			::= {vmConfigGroupEntry 2}

--------------------------------------------------------------------------------------------
--
--	FMS Config Port Table
--
--	The whole of the vmConfigPortTable has been deprecated.
--	It is currently still implemented for backwards compatability.
--
--------------------------------------------------------------------------------------------

vmConfigPortTable	OBJECT-TYPE
			SYNTAX			SEQUENCE OF VmConfigPortEntry
			ACCESS			not-accessible
			STATUS			deprecated
			DESCRIPTION
			"Table configuration options for all of the ports."
			::= {linkbuilderConfigPackage 3}

vmConfigPortEntry	OBJECT-TYPE
			SYNTAX			VmConfigPortEntry
			ACCESS			not-accessible
			STATUS			deprecated
			DESCRIPTION
			"Configuration options for a single port."
			INDEX			{vmConPortGroupIndex,vmConPortIndex}
			::= {vmConfigPortTable 1}

			VmConfigPortEntry ::= SEQUENCE {
						vmConPortGroupIndex			INTEGER,
						vmConPortIndex				INTEGER,
						vmConPortSquelch 	                INTEGER,
						vmConPortLinkPulse			INTEGER,
						vmConPortXoverSwitchState		INTEGER,
						vmConPortType				INTEGER
			}

vmConPortGroupIndex	OBJECT-TYPE
			SYNTAX			INTEGER (1..16)
			ACCESS			read-only
			STATUS			deprecated
			DESCRIPTION
			"This attribute uniquely identifies this group within the repeater, it is
			part of the index for the port table."
			::= {vmConfigPortEntry 1}

vmConPortIndex		OBJECT-TYPE
			SYNTAX			INTEGER (1..1024)
			ACCESS			read-only
			STATUS			deprecated
			DESCRIPTION
			"This attribute uniquely identifies this port within the group, it is
			part of the index for the port table."
			::= {vmConfigPortEntry 2}

vmConPortSquelch	OBJECT-TYPE
			SYNTAX			INTEGER {
							normal		(1),
							low		(2),
							notApplicable	(3)
							}
			ACCESS			read-write
			STATUS			deprecated
			DESCRIPTION
			"This attribute controls the 10BaseT squelch level for a 10BaseT port.
			It enables it to be set to the IEEE standard level = normal, or to be
			set more sensative = low."
			::= {vmConfigPortEntry 3}

vmConPortLinkPulse	OBJECT-TYPE
			SYNTAX			INTEGER {
							enabled		(1),
							disabled	(2),
							notApplicable	(3)
							}
			ACCESS			read-write
			STATUS			deprecated
			DESCRIPTION
			"This attribute determines if link pulse generating and monitoring is enabled
			or disabled for a 10BaseT port. The attribute may take
			the values of enabled (standard) or disabled (non standard)."
			::= {vmConfigPortEntry 4}

vmConPortXoverSwitchState OBJECT-TYPE
			SYNTAX			INTEGER {
							notApplicable		(1),
							normal			(2),
							crossed			(3)
							}
			ACCESS			read-only
			STATUS			deprecated
			DESCRIPTION
			"This attribute determines the state of the cross over switch, this is only
			applicable to fixed UTP ports."
			::= {vmConfigPortEntry 5}

vmConPortType		OBJECT-TYPE
			SYNTAX			INTEGER {
								fms-FixedTP		(1),
								fms-FixedCoax		(2),
								fms-FixedFibreFL	(3),
								fms-ModularBridge	(4),
								fms-ModularMaleAUI	(8),
								fms-ModularFMaleAUI	(9),
								fms-ModularCoax		(10),
								fms-ModularFibreFL	(11),
								fms-ModularUTP		(12),
								fms-ModularSTP		(13),
								fms-ModularFibreFB	(14),
								fms-AUI			(15),
								bti-FixedUTP		(32),
								bti-ModularFibreFL	(40),
								bti-ModularCoax		(41),
								bti-AUI			(50),
								unknown			(60)
							}
			ACCESS			read-only
			STATUS			deprecated
			DESCRIPTION
			"This attribute describes the port type in terms of media supported, modular
			 or fixed and manufacturer."
			::= {vmConfigPortEntry 6}

--------------------------------------------------------------------------------------------
--
--	Media Card Configuration
--
--	The whole of the vmConfigMediaTable has been deprecated.
--	It is currently still implemented for backwards compatability.
--
--------------------------------------------------------------------------------------------

vmConfigMediaTable	OBJECT-TYPE
			SYNTAX			SEQUENCE OF VmConfigMediaEntry
			ACCESS			not-accessible
			STATUS			deprecated
			DESCRIPTION
			"Configuration information and control variables for a collection of media cards
			this repeater."
			::= {linkbuilderConfigPackage 4}

vmConfigMediaEntry	OBJECT-TYPE
			SYNTAX			VmConfigMediaEntry
			ACCESS			not-accessible
			STATUS			deprecated
			DESCRIPTION
			"Configuration information and control variables for a single media card."
			INDEX			{vmConMediaIndex}
			::= {vmConfigMediaTable 1}

			VmConfigMediaEntry ::= SEQUENCE {
						vmConMediaIndex				INTEGER,
						vmConMediaModuleRevNo			INTEGER,
						vmConMediaModuleCardType		INTEGER
						}

vmConMediaIndex		OBJECT-TYPE
			SYNTAX			INTEGER (1..16)
			ACCESS			read-only
			STATUS			deprecated
			DESCRIPTION
			"This attribute uniquely identifies this media card, it is part of the
			index for the Media Table."
			::= {vmConfigMediaEntry 1}

vmConMediaModuleRevNo	OBJECT-TYPE
			SYNTAX			INTEGER (1..1024)
			ACCESS			read-only
			STATUS			deprecated
			DESCRIPTION
			"The Media Module Hardware revision number."
			::= {vmConfigMediaEntry 2}

vmConMediaModuleCardType OBJECT-TYPE
			SYNTAX			INTEGER {
							fms-12Port-UTP		(1),
							fms-10Port-Coax		(2),
							fms-12Port-Fibre	(3),
							fms-6Port-Fibre		(4),
							fms-24PortUTP		(5),
							bt-12Port-UTP-Rev2	(14),
							bt-12Port-UTP-Rev1	(15),
							bti-12Port-UTP-Rev2	(30),
							bti-12Port-UTP-Rev1	(31),
							fmsII-12Port-TP-RJ45	(65),
							fmsII-10Port-Coax	(66),
							fmsII-12Port-Fibre	(67),
							fmsII-6Port-Fibre	(68),
							fmsII-24Port-TP-RJ45	(69),
							fmsII-24Port-TP-Telco	(70),
							fmsII-RMON-Box		(71)
							}
			ACCESS			read-only
			STATUS			deprecated
			DESCRIPTION
			"The Media Module Card Type."
			::= {vmConfigMediaEntry 3}

--
--	Mac Monitor Table
--
--	The whole of the vmMacMonitorTable has been deprecated.
--	It is currently still implemented for backwards compatability.
--
vmMacMonitorTable		OBJECT-TYPE
			SYNTAX			SEQUENCE OF VmMacMonitorEntry
			ACCESS			not-accessible
			STATUS			deprecated
			DESCRIPTION
                       "Table of performance and error statistics for the
                      MACs."
			::= {linkbuilderMonitorMacPackage 1}

vmMacMonitorEntry	OBJECT-TYPE
			SYNTAX			VmMacMonitorEntry
			ACCESS			not-accessible
			STATUS			deprecated
			DESCRIPTION
			" "
			INDEX			{vmMacMonitorIndex}
			::= {vmMacMonitorTable 1}

			VmMacMonitorEntry ::= SEQUENCE {
						vmMacMonitorIndex			INTEGER,
						vmMacMonitorMissErrors			Counter,
						vmMacMonitorBabbleErrors		Counter,
						vmMacMonitorMemoryErrors		Counter,
						vmMacMonitorFCSErrors			Counter,
						vmMacMonitorOverflowErrors		Counter,
						vmMacMonitorFramingErrors		Counter,
						vmMacMonitorRetryErrors			Counter,
						vmMacMonitorLateEvents			Counter,
						vmMacMonitorLCarErrors			Counter,
						vmMacMonitorUnderflowErrors		Counter
			}

vmMacMonitorIndex OBJECT-TYPE
			SYNTAX			INTEGER (1..16)
			ACCESS			read-only
			STATUS			deprecated
			DESCRIPTION
                      "This object identifies the MAC for
                      which this entry contains information."
			::= {vmMacMonitorEntry 1}

vmMacMonitorMissErrors	OBJECT-TYPE
			SYNTAX			Counter
			ACCESS			read-only
			STATUS			deprecated
			DESCRIPTION
                      "The number of packets the MAC has failed to receive.
                      This may be due to no receive buffer being available
                      or a SILO overflow."
			::= {vmMacMonitorEntry 2}

vmMacMonitorBabbleErrors	OBJECT-TYPE
			SYNTAX			Counter
			ACCESS			read-only
			STATUS			deprecated
			DESCRIPTION
                      "The number of packets, whose length has exceeded 1519
                       bytes, transmitted by the MAC."
			::= {vmMacMonitorEntry 3}

vmMacMonitorMemoryErrors	OBJECT-TYPE
			SYNTAX			Counter
			ACCESS			read-only
			STATUS			deprecated
			DESCRIPTION
                      "The number of times the MAC has been unable to obtain
                      bus mastership with the specified period."
			::= {vmMacMonitorEntry 4}

vmMacMonitorFCSErrors	OBJECT-TYPE
			SYNTAX			Counter
			ACCESS			read-only
			STATUS			deprecated
			DESCRIPTION
                      "The number packets received by the MAC containing
                      an FCS error."
			::= {vmMacMonitorEntry 5}

vmMacMonitorOverflowErrors	OBJECT-TYPE
			SYNTAX			Counter
			ACCESS			read-only
			STATUS			deprecated
			DESCRIPTION
                      "The number of packets received by the MAC which caused
                      a SILO overflow error."
			::= {vmMacMonitorEntry 6}

vmMacMonitorFramingErrors	OBJECT-TYPE
			SYNTAX			Counter
			ACCESS			read-only
			STATUS			deprecated
			DESCRIPTION
                      "The number of packets received by the MAC containing a
                      non-integer multiple of 8 bits and a FCS error."
			::= {vmMacMonitorEntry 7}

vmMacMonitorRetryErrors	OBJECT-TYPE
			SYNTAX			Counter
			ACCESS			read-only
			STATUS			deprecated
			DESCRIPTION
                      "The number of times the MAC has failed, in 16 attempts,
                      to transmit a packet due to collisions on the network."
			::= {vmMacMonitorEntry 8}

vmMacMonitorLateEvents	OBJECT-TYPE
			SYNTAX			Counter
			ACCESS			read-only
			STATUS			deprecated
			DESCRIPTION
                      "The number of times the MAC detected an out of
                      window collision during transmission of a packet."
			::= {vmMacMonitorEntry 9}

vmMacMonitorLCarErrors	OBJECT-TYPE
			SYNTAX			Counter
			ACCESS			read-only
			STATUS			deprecated
			DESCRIPTION
                      "The number of times the MAC has detected a loss of
                      carrier during transmission of a packet."
			::= {vmMacMonitorEntry 10}

vmMacMonitorUnderflowErrors	OBJECT-TYPE
			SYNTAX			Counter
			ACCESS			read-only
			STATUS			deprecated
			DESCRIPTION
                      "The number of times the MAC has truncated an outgoing
                      packet due to the SILO emptying before the end of packet
                      has been reached."
			::= {vmMacMonitorEntry 11}

--
--			Trap definitions
--

vmMauMediaAvailable TRAP-TYPE
		ENTERPRISE		a3Com
		VARIABLES		{
					 rpMauMediaAvailable
					}
		DESCRIPTION
		"This trap indicates that the mau for this port has entered or
		 left rpMauMediaAvailable = available(3) state."
		::=			25

vmAutoPartitionState TRAP-TYPE
		ENTERPRISE		a3Com
		VARIABLES		{
					 rptrPortAutoPartitionState
					}
		DESCRIPTION
		"This trap indicates that the repeater SM for this port has entered
		 or left the partitioned state."
		::=			26

------------------------------------------------------------------------------------------
--											--
--						Start of 				--
--						PDDRM Generic Repeater MIB.		--
--											--
------------------------------------------------------------------------------------------

pddrmBasicPackage	OBJECT IDENTIFIER ::= { repeaterMgmt 1}
pddrmMonitorPackage	OBJECT IDENTIFIER ::= { repeaterMgmt 2}

pddrmBasRepeaterPackage	OBJECT IDENTIFIER ::= { pddrmBasicPackage 1 }
pddrmBasGroupPackage	OBJECT IDENTIFIER ::= { pddrmBasicPackage 2 }
pddrmBasPortPackage	OBJECT IDENTIFIER ::= { pddrmBasicPackage 3 }

pddrmMonRepeaterPackage	OBJECT IDENTIFIER ::= { pddrmMonitorPackage 1}
pddrmMonGroupPackage	OBJECT IDENTIFIER ::= { pddrmMonitorPackage 2}
pddrmMonPortPackage	OBJECT IDENTIFIER ::= { pddrmMonitorPackage 3}
pddrmMonRepeaterDummyPackage	OBJECT IDENTIFIER ::= { pddrmMonitorPackage 4}
pddrmMonGroupDummyPackage	OBJECT IDENTIFIER ::= { pddrmMonitorPackage 5}
pddrmMonPortDummyPackage	OBJECT IDENTIFIER ::= { pddrmMonitorPackage 6}

------------------------------------------------------------------------------------------
--											--
--						Start of				--
--						Basic Group				--
--											--
------------------------------------------------------------------------------------------

--
--	PDDRM Basic Repeater Table
--

--
--	PDDRM Basic Group Table
--

--
--	PDDRM Basic Port Table
--

------------------------------------------------------------------------------------------
--											--
--						End of					--
--						PDDRM Basic Group				--
--											--
------------------------------------------------------------------------------------------
------------------------------------------------------------------------------------------
--											--
--						Start of				--
--						PDDRM Monitor Group			--
--											--
------------------------------------------------------------------------------------------

--
--	PDDRM Monitor Repeater Level Objects
--

pddrmMonRepeaterReadableFrames OBJECT-TYPE
			SYNTAX			Counter
			ACCESS			read-only
			STATUS			deprecated
			DESCRIPTION
			"This counter is incremented by one for each frame whose OctetCount
			is greater than or equal to minFrameSize and less than or equal to
			maxFraneSize and for which FCSError is not asserted that is received
			by the repeater."
			::= {pddrmMonRepeaterPackage 1}

pddrmMonRepeaterReadableOctets	OBJECT-TYPE
			SYNTAX			Counter
			ACCESS			read-only
			STATUS			deprecated
			DESCRIPTION
			"This counter is incremented by the octet count for each readable
			frame received by the repeater."
			::= {pddrmMonRepeaterPackage 2}

pddrmMonRepeaterFCSErrors OBJECT-TYPE
			SYNTAX			Counter
			ACCESS			read-only
			STATUS			deprecated
			DESCRIPTION
			"This counter is incremented by one for each frame with an FCS error
			that does not have a framing error and which is of legal frame size
			received by the repeater."
			::= {pddrmMonRepeaterPackage 3}

pddrmMonRepeaterAlignmentErrors OBJECT-TYPE
			SYNTAX			Counter
			ACCESS			read-only
			STATUS			deprecated
			DESCRIPTION
			"This counter is incremented by one for each frame with an FCS error
			that does have a framing error and which is of legal frame size
			received by the repeater."
			::= {pddrmMonRepeaterPackage 4}

pddrmMonRepeaterFrameTooLongs OBJECT-TYPE
			SYNTAX			Counter
			ACCESS			read-only
			STATUS			deprecated
			DESCRIPTION
			"This counter is incremented by one for each frame whose octet count
			is greater than the max frame size that is received by the repeater."
			::= {pddrmMonRepeaterPackage 5}

pddrmMonRepeaterShortEvents OBJECT-TYPE
			SYNTAX			Counter
			ACCESS			read-only
			STATUS			deprecated
			DESCRIPTION
			"This counter is incremented by one for each carrier event whose
			duration is less than short event max time that is detected by the
			repeater."
			::= {pddrmMonRepeaterPackage 6}

pddrmMonRepeaterRunts	OBJECT-TYPE
			SYNTAX			Counter
			ACCESS			read-only
			STATUS			deprecated
			DESCRIPTION
			"This counter is incremented by one for each carrier event whose
			duration is greater than short event max time and less than valid
			packet min time and which does not suffer a collision detected by
			the repeater."
			::= {pddrmMonRepeaterPackage 7}

pddrmMonRepeaterCollisions  OBJECT-TYPE
			SYNTAX			Counter
			ACCESS			read-only
			STATUS			deprecated
			DESCRIPTION
			"This counter is incremented by one each time the repeater state
			machine enters the COLLISION COUNT INCREMENT state."
			::= {pddrmMonRepeaterPackage 8}

pddrmMonRepeaterLateEvents OBJECT-TYPE
			SYNTAX			Counter
			ACCESS			read-only
			STATUS			deprecated
			DESCRIPTION
			"This counter is incremented by one each time a collisions occurs
			after valid packet min time, a late event is counted as both a
			collision and as a late event."
			::= {pddrmMonRepeaterPackage 9}

pddrmMonRepeaterVeryLongEvents OBJECT-TYPE
			SYNTAX			Counter
			ACCESS			read-only
			STATUS			deprecated
			DESCRIPTION
			"This counter is incremented by one each time a carrier event
			occurs whose duration is greater than the MAU Jabber Lockup
			Protection time."
			::= {pddrmMonRepeaterPackage 10}

pddrmMonRepeaterDataRateMismatches OBJECT-TYPE
			SYNTAX			Counter
			ACCESS			read-only
			STATUS			deprecated
			DESCRIPTION
			"This counter is incremented by one each time a packet has been received
			by this repeater with the data rate detectably mismatched from the local
			frequency."
			::= {pddrmMonRepeaterPackage 11}

pddrmMonRepeaterAutoPartitions OBJECT-TYPE
			SYNTAX			Counter
			ACCESS			read-only
			STATUS			deprecated
			DESCRIPTION
			"This counter is incremented by one each time the repeater has automatically
			partitioned any port."
			::= {pddrmMonRepeaterPackage 12}

pddrmMonRepeaterUniCastFrames OBJECT-TYPE
			SYNTAX			Counter
			ACCESS			read-only
			STATUS			deprecated
			DESCRIPTION
			"This counter is incremented by one for each readable frame seen by the
			repeater that is addressed to a unicast (non group) address."
			::= {pddrmMonRepeaterPackage 13}

pddrmMonRepeaterMultiCastFrames OBJECT-TYPE
			SYNTAX			Counter
			ACCESS			read-only
			STATUS			deprecated
			DESCRIPTION
			"This counter is incremented by one for each readable frame seen by the
			repeater that is addressed to a multicast (non broadcast) address."
			::= {pddrmMonRepeaterPackage 14}

pddrmMonRepeaterBroadCastFrames OBJECT-TYPE
			SYNTAX			Counter
			ACCESS			read-only
			STATUS			deprecated
			DESCRIPTION
			"This counter is incremented by one for each readable frame seen by the
			repeater that is addressed to the broadcast address."
			::= {pddrmMonRepeaterPackage 15}

pddrmMonRepeaterClearCounters OBJECT-TYPE
			SYNTAX			INTEGER {
							noChangeCounters	(1),
							clearCounters		(2)
							}
			ACCESS			write-only
			STATUS			deprecated
			DESCRIPTION
			"This attribute allows all counters on this repeater to be cleared."
			::= {pddrmMonRepeaterPackage 16}

pddrmMonRepeaterMediaAvailableTraps OBJECT-TYPE
			SYNTAX			INTEGER {
							enableMediaTraps	(1),
							disableMediaTraps	(2)
							}
			ACCESS			read-write
			STATUS			deprecated
			DESCRIPTION
			"This attribute enable/disables traps to be issued when a ports
			 media is lost/regained."
			::= {pddrmMonRepeaterPackage 17}

pddrmMonRepeaterAutoPartitionTraps OBJECT-TYPE
			SYNTAX			INTEGER {
							enablePartitionTraps	(1),
							disablePartitionTraps	(2)
							}
			ACCESS			read-write
			STATUS			deprecated
			DESCRIPTION
			"This attribute enables/disables traps to be issued when ports
			 autopartition or reconnect."
			::= {pddrmMonRepeaterPackage 18}

pddrmMonRepeaterTotalErrors OBJECT-TYPE
                        SYNTAX                  Counter
                        ACCESS                  read-only
                        STATUS                  deprecated
                        DESCRIPTION
                        "This counter is incremented by one for each erroneous frame seen by the
                        repeater."
                        ::= {pddrmMonRepeaterPackage 19}

--
--
--	PDDRM Monitor Group Table
--

pddrmMonitorGroupTable	OBJECT-TYPE
			SYNTAX			SEQUENCE OF PddrmMonitorGroupEntry
			ACCESS			not-accessible
			STATUS			deprecated
			DESCRIPTION
			"Status information and control variables for a collection of groups in
			this repeater."
			::= {pddrmMonGroupPackage 1}

pddrmMonitorGroupEntry	OBJECT-TYPE
			SYNTAX			PddrmMonitorGroupEntry
			ACCESS			not-accessible
			STATUS			deprecated
			DESCRIPTION
			"Status information and control variables for a single group of
			ports."
			INDEX			{pddrmMonGroupIndex}
			::= {pddrmMonitorGroupTable 1}

			PddrmMonitorGroupEntry ::= SEQUENCE {
						pddrmMonGroupIndex			INTEGER,
						pddrmMonGroupFCSErrors			Counter,
						pddrmMonGroupAlignmentErrors		Counter,
						pddrmMonGroupFrameTooLongs		Counter,
						pddrmMonGroupShortEvents		Counter,
						pddrmMonGroupRunts			Counter,
						pddrmMonGroupCollisions			Counter,
						pddrmMonGroupLateEvents			Counter,
						pddrmMonGroupVeryLongEvents		Counter,
						pddrmMonGroupDataRateMismatches		Counter,
						pddrmMonGroupAutoPartitions		Counter,
						pddrmMonGroupUniCastFrames		Counter,
						pddrmMonGroupMultiCastFrames		Counter,
						pddrmMonGroupBroadCastFrames		Counter,
						pddrmMonGroupClearCounters		INTEGER
						}

pddrmMonGroupIndex		OBJECT-TYPE
			SYNTAX			INTEGER (1..16)
			ACCESS			read-only
			STATUS			deprecated
			DESCRIPTION
			"This attribute uniquely identifies this group, it is part of the
			index for the Group Table."
			::= {pddrmMonitorGroupEntry 1}

pddrmMonGroupFCSErrors OBJECT-TYPE
			SYNTAX			Counter
			ACCESS			read-only
			STATUS			deprecated
			DESCRIPTION
			"This counter is incremented by one for each frame with an FCS error
			that does not have a framing error and which is of legal frame size."
			::= {pddrmMonitorGroupEntry 4}

pddrmMonGroupAlignmentErrors OBJECT-TYPE
			SYNTAX			Counter
			ACCESS			read-only
			STATUS			deprecated
			DESCRIPTION
			"This counter is incremented by one for each frame with an FCS error
			that does have a framing error and which is of legal frame size ."
			::= {pddrmMonitorGroupEntry 5}

pddrmMonGroupFrameTooLongs OBJECT-TYPE
			SYNTAX			Counter
			ACCESS			read-only
			STATUS			deprecated
			DESCRIPTION
			"This counter is incremented by one for each frame whose octet count
			is greater than the max frame size that is received by the repeater."
			::= {pddrmMonitorGroupEntry 6}

pddrmMonGroupShortEvents	OBJECT-TYPE
			SYNTAX			Counter
			ACCESS			read-only
			STATUS			deprecated
			DESCRIPTION
			"This counter is incremented by one for each carrier event whose
			duration is less than short event max time that is detected."
			::= {pddrmMonitorGroupEntry 7}

pddrmMonGroupRunts		OBJECT-TYPE
			SYNTAX			Counter
			ACCESS			read-only
			STATUS			deprecated
			DESCRIPTION
			"This counter is incremented by one for each carrier event whose
			duration is greater than short event max time and less than valid
			packet min time and which does not suffer a collision."
			::= {pddrmMonitorGroupEntry 8}

pddrmMonGroupCollisions	OBJECT-TYPE
			SYNTAX			Counter
			ACCESS			read-only
			STATUS			deprecated
			DESCRIPTION
			"This counter is incremented by one each time the repeater state
			machine enters the COLLISION COUNT INCREMENT state."
			::= {pddrmMonitorGroupEntry 9}

pddrmMonGroupLateEvents OBJECT-TYPE
			SYNTAX			Counter
			ACCESS			read-only
			STATUS			deprecated
			DESCRIPTION
			"This counter is incremented by one each time a collisions occurs
			after valid packet min time, a late event is counted as both a
			collision and as a late event."
			::= {pddrmMonitorGroupEntry 10}

pddrmMonGroupVeryLongEvents OBJECT-TYPE
			SYNTAX			Counter
			ACCESS			read-only
			STATUS			deprecated
			DESCRIPTION
			"This counter is incremented by one each time a carrier event
			occurs whose duration is greater than the MAU Jabber Lockup
			Protection time."
			::= {pddrmMonitorGroupEntry 11}

pddrmMonGroupDataRateMismatches OBJECT-TYPE
			SYNTAX			Counter
			ACCESS			read-only
			STATUS			deprecated
			DESCRIPTION
			"This counter is incremented by one each time a packet has been received
			with the data rate detectably mismatched from the local frequency."
			::= {pddrmMonitorGroupEntry 12}

pddrmMonGroupAutoPartitions OBJECT-TYPE
			SYNTAX			Counter
			ACCESS			read-only
			STATUS			deprecated
			DESCRIPTION
			"This counter is incremented by one each time the repeater has automatically
			partitioned any port."
			::= {pddrmMonitorGroupEntry 13}

pddrmMonGroupUniCastFrames OBJECT-TYPE
			SYNTAX			Counter
			ACCESS			read-only
			STATUS			deprecated
			DESCRIPTION
			"This counter is incremented by one for each readable frame seen by the
			group that is addressed to a unicast (non group) address."
			::= {pddrmMonitorGroupEntry 14}

pddrmMonGroupMultiCastFrames OBJECT-TYPE
			SYNTAX			Counter
			ACCESS			read-only
			STATUS			deprecated
			DESCRIPTION
			"This counter is incremented by one for each readable frame seen by the
			group that is addressed to a multicast (non broadcast) address."
			::= {pddrmMonitorGroupEntry 15}

pddrmMonGroupBroadCastFrames OBJECT-TYPE
			SYNTAX			Counter
			ACCESS			read-only
			STATUS			deprecated
			DESCRIPTION
			"This counter is incremented by one for each readable frame seen by the
			group that is addressed to the broadcast address."
			::= {pddrmMonitorGroupEntry 16}

pddrmMonGroupClearCounters OBJECT-TYPE
			SYNTAX			INTEGER {
							noChangeCounters	(1),
							clearCounters		(2)
							}
			ACCESS			write-only
			STATUS			deprecated
			DESCRIPTION
			"This attribute allows all counters on this Group to be cleared."
			::= {pddrmMonitorGroupEntry 17}

--
--	PDDRM Monitor Port Table
--

pddrmMonitorPortTable	OBJECT-TYPE
			SYNTAX			SEQUENCE OF PddrmMonitorPortEntry
			ACCESS			not-accessible
			STATUS			deprecated
			DESCRIPTION
			"Table of performance and error statistics for the ports."
			::= {pddrmMonPortPackage 1}

pddrmMonitorPortEntry	OBJECT-TYPE
			SYNTAX			PddrmMonitorPortEntry
			ACCESS			not-accessible
			STATUS			deprecated
			DESCRIPTION
			"Performance and error statistics for a single port."
			INDEX			{pddrmMonPortGroupIndex,
						 pddrmMonPortIndex}
			::= {pddrmMonitorPortTable 1}

			PddrmMonitorPortEntry ::= SEQUENCE {
						pddrmMonPortGroupIndex			INTEGER,
						pddrmMonPortIndex			INTEGER,
						pddrmMonPortUniCastFrames		Counter,
						pddrmMonPortMultiCastFrames		Counter,
						pddrmMonPortBroadCastFrames		Counter,
						pddrmMonPortClearCounters		INTEGER,
						pddrmMonPortESTFilter			INTEGER,
						pddrmMonPortMediaAvailableTraps		INTEGER,
						pddrmMonPortAutoPartitionTraps		INTEGER
							}

pddrmMonPortGroupIndex	OBJECT-TYPE
			SYNTAX			INTEGER (1..16)
			ACCESS			read-only
			STATUS			deprecated
			DESCRIPTION
			"This attribute uniquely identifies this group within the repeater, it is
			part of the index for the port table."
			::= {pddrmMonitorPortEntry 1}

pddrmMonPortIndex		OBJECT-TYPE
			SYNTAX			INTEGER (1..1024)
			ACCESS			read-only
			STATUS			deprecated
			DESCRIPTION
			"This attribute uniquely identifies this port within the group, it is
			part of the index for the port table."
			::= {pddrmMonitorPortEntry 2}

pddrmMonPortUniCastFrames OBJECT-TYPE
			SYNTAX			Counter
			ACCESS			read-only
			STATUS			deprecated
			DESCRIPTION
			"This counter is incremented by one for each readable frame seen by the
			group that is addressed to a unicast (non group) address."
			::= {pddrmMonitorPortEntry 3}

pddrmMonPortMultiCastFrames OBJECT-TYPE
			SYNTAX			Counter
			ACCESS			read-only
			STATUS			deprecated
			DESCRIPTION
			"This counter is incremented by one for each readable frame seen by the
			group that is addressed to a multicast (non broadcast) address."
			::= {pddrmMonitorPortEntry 4}

pddrmMonPortBroadCastFrames OBJECT-TYPE
			SYNTAX			Counter
			ACCESS			read-only
			STATUS			deprecated
			DESCRIPTION
			"This counter is incremented by one for each readable frame seen by the
			group that is addressed to the broadcast address."
			::= {pddrmMonitorPortEntry 5}

pddrmMonPortClearCounters OBJECT-TYPE
			SYNTAX			INTEGER {
							noChangeCounters	(1),
							clearCounters		(2)
							}
			ACCESS			write-only
			STATUS			deprecated
			DESCRIPTION
			"This attribute allows all counters on this Port to be cleared."
			::= {pddrmMonitorPortEntry 6}

pddrmMonPortESTFilter	 OBJECT-TYPE
			SYNTAX			INTEGER {
							filter			(1),
							pass			(2)
							}
			ACCESS			read-write
			STATUS			deprecated
			DESCRIPTION
			"This attribute passes or filters out entries from this port from
			 going to the End Station Table processing. For instance the
			 backbone port on a repeater would normally have this atribute
			 set to filter, while the UTP ports would normally have this set to
			 pass."
			::= {pddrmMonitorPortEntry 7}

pddrmMonPortMediaAvailableTraps OBJECT-TYPE
                        SYNTAX                  INTEGER {
                                                        enableMediaTraps        (1),
                                                        disableMediaTraps       (2)
                                                        }
                        ACCESS                  read-write
                        STATUS                  deprecated
                        DESCRIPTION
                        "This attribute enable/disables traps to be issued when a ports
                         media is lost/regained."
                        ::= {pddrmMonitorPortEntry 8}

pddrmMonPortAutoPartitionTraps OBJECT-TYPE
                        SYNTAX                  INTEGER {
                                                        enablePartitionTraps    (1),
                                                        disablePartitionTraps   (2)
                                                        }
                        ACCESS                  read-write
                        STATUS                  deprecated
                        DESCRIPTION
                        "This attribute enables/disables traps to be issued when ports
                         autopartition or reconnect."
                        ::= {pddrmMonitorPortEntry 9}


------------------------------------------------------------------------------------------
--											--
--	The whole of the a3Com(43).linkBuilder10BTi-mib(8).snmpDot3RptrMgt(4)		--
--	group has been deprecated.							--
--	The group is currently still implemented for backwards compatability,		--
--	but all new applications should use mib-2(1).snmpDot3RptrMgt(22) instead.	--
--											--
------------------------------------------------------------------------------------------

deprSnmpDot3RptrMgt		OBJECT IDENTIFIER ::= {linkBuilder10BTi-mib 4}

deprRptrBasicPackage		OBJECT IDENTIFIER ::= {deprSnmpDot3RptrMgt 1}
deprRptrMonitorPackage		OBJECT IDENTIFIER ::= {deprSnmpDot3RptrMgt 2}
deprRptrAddrTrackPackage	OBJECT IDENTIFIER ::= {deprSnmpDot3RptrMgt 3}

deprRptrRptrInfo		OBJECT IDENTIFIER ::= {deprRptrBasicPackage 1}
deprRptrGroupInfo		OBJECT IDENTIFIER ::= {deprRptrBasicPackage 2}
deprRptrPortInfo		OBJECT IDENTIFIER ::= {deprRptrBasicPackage 3}

deprRptrMonitorRptrInfo		OBJECT IDENTIFIER ::= {deprRptrMonitorPackage 1}
deprRptrMonitorGroupInfo	OBJECT IDENTIFIER ::= {deprRptrMonitorPackage 2}
deprRptrMonitorPortInfo		OBJECT IDENTIFIER ::= {deprRptrMonitorPackage 3}

deprRptrAddrTrackRptrInfo	OBJECT IDENTIFIER ::= {deprRptrAddrTrackPackage 1}
deprRptrAddrTrackGroupInfo	OBJECT IDENTIFIER ::= {deprRptrAddrTrackPackage 2}
deprRptrAddrTrackPortInfo	OBJECT IDENTIFIER ::= {deprRptrAddrTrackPackage 3}

------------------------------------------------------------------------------------------
--											--
--			Start of							--
--			Basic Group (deprecated)					--
--											--
------------------------------------------------------------------------------------------

--
--	Basic Repeater
--

deprRptrGroupCapacity	OBJECT-TYPE
			SYNTAX			INTEGER (1..32)
			ACCESS			read-only
			STATUS			deprecated
			DESCRIPTION
			 "The deprRptrGroupCapacity is the number of groups
                      that can be contained within the repeater. Within
                      each managed repeater, the groups are uniquely
                      numbered in the range from 1 to deprRptrGroupCapacity.

                      Some groups may not be present in a given repeater
                      instance, in which case the actual number of
                      groups present will be less than
                      deprRptrGroupCapacity. The number of groups present
                      will never be greater than deprRptrGroupCapacity.

                      Note:  In practice, this will generally be the
                      number of field-replaceable units (i.e., modules,
                      cards, or boards) that can fit in the physical
                      repeater enclosure, and the group numbers  will
                      correspond to numbers marked on the physical
                      enclosure."
			::= {deprRptrRptrInfo 1}

deprRptrOperStatus		OBJECT-TYPE
			SYNTAX		INTEGER {
						other(1),		-- undefined or unknown
						ok(2),			-- no known failures
						rptrFailure(3), 	-- repeater related fail
						groupFailure(4),	-- group related failure
						portFailure(5),		-- port related failure
						generalFailure(6) 	-- failure, unspecified
						}
			ACCESS			read-only
			STATUS			deprecated
			DESCRIPTION
                      "The deprRptrOperStatus object indicates the
                      operational state of the repeater. The
                      deprRptrHealthText object may be consulted for more
                      specific information about the state of the
                      repeater's health.

                      In the case of multiple kinds of failures (e.g.,
                      repeater failure and port failure), the value of
                      this attribute shall reflect the highest priority
                      failure in the following order:
                          rptrFailure(3)
                          groupFailure(4)
                          portFailure(5)
                          generalFailure(6)"
			::= {deprRptrRptrInfo 2}

deprRptrHealthText		OBJECT-TYPE
			SYNTAX			DisplayString (SIZE (0..255))
			ACCESS			read-only
			STATUS			deprecated
			DESCRIPTION
                      "The health text object is a text string that
                      provides information relevant to the operational
                      state of the repeater. Agents may use this
                      mechanism to provide detailed failure information
                      or instructions for problem resolution. The
                      contents are agent-specific."
			::= {deprRptrRptrInfo 3}

deprRptrReset		 OBJECT-TYPE
			SYNTAX			INTEGER {
							noReset(1),
							reset(2)
							}
			ACCESS			read-write
			STATUS			deprecated
			DESCRIPTION
                      "Setting this variable to reset(2) causes a
                      transition to the START state of Fig 9-2 in
                      section 9 [11].

                      Setting this variable to noReset(1) has no effect.
                      The agent will always return the value noReset(1)
                      when this variable is read.

                      This action does not reset the management counters
                      defined in this document nor does it affect the
                      portAdminState parameters. Included in this action
                      is the execution of a disruptive Self-Test.  As a
                      result of this action a deprRptrReset trap may be
                      sent.

                      Note:  This action may result in the loss of
                      packets."
			::= {deprRptrRptrInfo 4}

deprRptrNonDisruptTest	OBJECT-TYPE
			SYNTAX			INTEGER {
							noSelfTest(1),
							selfTest(2)
							}
			ACCESS			read-write
			STATUS			deprecated
			DESCRIPTION
                      "Setting this variable to selfTest(2) causes the
                      repeater to perform a agent-specific, non-
                      disruptive self-test that has the following
                      characteristics: (1)  The nature of the tests is
                      not specified. (2)  The test does not change the
                      state of the repeater or management information
                      about the repeater. (3)  The test does not inject
                      packets onto any segment. (4)  The test does not
                      prevent the relay of any packets. (5)  The test
                      does not interfere with management functions.

                      After performing this test the agent will update
                      the repeater health information. If a change in
                      the repeater health has occurred, the agent will
                      send a deprRptrHealth trap.

                      Setting this variable to noSelfTest(1) has no
                      effect. The agent will always return the value
                      noSelfTest(1) when this variable is read."
			::= {deprRptrRptrInfo 5}

deprRptrTotalPartitionedPorts	OBJECT-TYPE
			SYNTAX			Gauge
			ACCESS			read-only
			STATUS			deprecated
			DESCRIPTION
                      "This object returns the total number of ports in
                      the repeater whose current state meets all three
                      of the following criteria:  deprRptrPortOperStatus
                      does not have the value notPresent(3),
                      deprRptrPortAdminStatus is enabled(1), and
                      deprRptrPortAutoPartitionState is autoPartitioned(1)."
			::= {deprRptrRptrInfo 6}

--
--	Basic Group Table
--

deprRptrGroupTable		OBJECT-TYPE
			SYNTAX			SEQUENCE OF DeprRptrGroupEntry
			ACCESS			not-accessible
			STATUS			deprecated
			DESCRIPTION
                      "Table of descriptive and status information about
                      the groups of ports."
			::= {deprRptrGroupInfo 1}

deprRptrGroupEntry		OBJECT-TYPE
			SYNTAX			DeprRptrGroupEntry
			ACCESS			not-accessible
			STATUS			deprecated
			DESCRIPTION
                      "An entry in the table, containing information
                      about a single group of ports."
			INDEX			{deprRptrGroupIndex}
			::= {deprRptrGroupTable 1}

			DeprRptrGroupEntry ::= SEQUENCE {
						deprRptrGroupIndex			INTEGER,
						deprRptrGroupDescr			DisplayString,
						deprRptrGroupObjectID			OBJECT IDENTIFIER,
						deprRptrGroupOperStatus			INTEGER,
						deprRptrGroupLastOperStatusChange	TimeTicks,
						deprRptrGroupPortCapacity		INTEGER
			}

deprRptrGroupIndex		OBJECT-TYPE
			SYNTAX			INTEGER (1..1024)
			ACCESS			read-only
			STATUS			deprecated
			DESCRIPTION
                      "This variable identifies the group within the
                      repeater for which this entry contains
                      information. This value is never greater than
                      deprRptrGroupCapacity."
			::= {deprRptrGroupEntry 1}

deprRptrGroupDescr		OBJECT-TYPE
			SYNTAX			DisplayString (SIZE (0..255))
			ACCESS			read-only
			STATUS			deprecated
			DESCRIPTION
                      "A textual description of the group. This value
                      should include the full name and version
                      identification of the group's hardware type and
                      indicate how the group is differentiated from
                      other groups in the repeater.  'Wilma Flintstone
                      6-Port FOIRL Plug-in Module, Rev A' or 'Barney
                      Rubble 10BASE-T 4-port SIMM socket V. 2.1' are
                      examples of valid group descriptions.

                      It is mandatory that this only contain printable
                      ASCII characters."
			::= {deprRptrGroupEntry 2}

deprRptrGroupObjectID	OBJECT-TYPE
			SYNTAX			OBJECT IDENTIFIER
			ACCESS			read-only
			STATUS			deprecated
			DESCRIPTION
                      "The vendor's authoritative identification of the
                      group.  This value is allocated within the SMI
                      enterprises subtree (1.3.6.1.4.1) and provides a
                      straight-forward and unambiguous means for
                      determining what kind of group is being managed.

                      For example, this variable could take the value
                      1.3.6.1.4.1.4242.1.2.14 if vendor 'Flintstones,
                      Inc.' was assigned the subtree 1.3.6.1.4.1.4242,
                      and had assigned the identifier
                      1.3.6.1.4.1.4242.1.2.14 to its 'Wilma Flintstone
                      6-Port FOIRL Plug-in Module.'"
			::= {deprRptrGroupEntry 3}

deprRptrGroupOperStatus	OBJECT-TYPE
			SYNTAX			INTEGER {
							other(1),
							operational(2),
							malFunctioning(3),
							notPresent(4),
							undertest(5),
							resetInProgress(6)
							}
			ACCESS			read-only
			STATUS			deprecated
			DESCRIPTION
                      "An object that indicates the operational status
                      of the group.

                      A status of notPresent(4) indicates that the group
                      has been physically removed from the repeater. A
                      status of operational(2) indicates that the group
                      is functioning, and a status of malFunctioning(3)
                      indicates that the group is malfunctioning in some
                      way."
			::= {deprRptrGroupEntry 4}

deprRptrGroupLastOperStatusChange		OBJECT-TYPE
			SYNTAX			TimeTicks
			ACCESS			read-only
			STATUS			deprecated
			DESCRIPTION
                      "An object that contains the value of sysUpTime at
                      the time that the value of the deprRptrGroupOperStatus
                      object for this group last changed.

                      A value of zero indicates that the group's oper
                      status has not changed since the agent last
                      restarted."
			::= {deprRptrGroupEntry 5}

deprRptrGroupPortCapacity	OBJECT-TYPE
			SYNTAX			INTEGER (1..1024)
			ACCESS			read-only
			STATUS			deprecated
			DESCRIPTION
                      "The deprRptrGroupPortCapacity is the number of ports
                      that can be contained within the group.  Valid
                      range is 1-1024. Within each group, the ports are
                      uniquely numbered in the range from 1 to
                      deprRptrGroupPortCapacity.

                      Note:  In practice, this will generally be the
                      number of ports on a module, card, or board, and
                      the port numbers will correspond to numbers marked
                      on the physical embodiment."
			::= {deprRptrGroupEntry 6}

--
--	Basic Port Table
--

deprRptrPortTable		OBJECT-TYPE
			SYNTAX			SEQUENCE OF DeprRptrPortEntry
			ACCESS			not-accessible
			STATUS			deprecated
			DESCRIPTION
                      "Table of descriptive and status information about
                      the ports."
			::= {deprRptrPortInfo 1}

deprRptrPortEntry		OBJECT-TYPE
			SYNTAX			DeprRptrPortEntry
			ACCESS			not-accessible
			STATUS			deprecated
			DESCRIPTION
                      "An entry in the table, containing information
                      about a single port."
			INDEX			{deprRptrPortGroupIndex,deprRptrPortIndex}
			::= {deprRptrPortTable 1}

			DeprRptrPortEntry ::= SEQUENCE {
						deprRptrPortGroupIndex		INTEGER,
						deprRptrPortIndex		INTEGER,
						deprRptrPortAdminStatus		INTEGER,
						deprRptrPortAutoPartitionState	INTEGER,
						deprRptrPortOperStatus		INTEGER
			}

deprRptrPortGroupIndex	OBJECT-TYPE
			SYNTAX			INTEGER (1..1024)
			ACCESS			read-only
			STATUS			deprecated
			DESCRIPTION
                      "This variable identifies the group containing the
                      port for which this entry contains information."
			::= {deprRptrPortEntry 1}

deprRptrPortIndex		OBJECT-TYPE
			SYNTAX			INTEGER (1..1024)
			ACCESS			read-only
			STATUS			deprecated
			DESCRIPTION
                      "This variable identifies the port within the
                      group within the repeater for which this entry
                      contains management information. This value can
                      never be greater than deprRptrGroupPortCapacity for
                      the associated group."
			::= {deprRptrPortEntry 2}

deprRptrPortAdminStatus	OBJECT-TYPE
			SYNTAX			INTEGER {
							enabled(1),
							disabled(2)
							}
			ACCESS			read-write
			STATUS			deprecated
			DESCRIPTION
                      "Setting this object to disabled(2) disables the
                      port.  A disabled port neither transmits nor
                      receives.  Once disabled, a port must be
                      explicitly enabled to restore operation.  A port
                      which is disabled when power is lost or when a
                      reset is exerted shall remain disabled when normal
                      operation resumes.

                      The admin status takes precedence over auto-
                      partition and functionally operates between the
                      auto-partition mechanism and the AUI/PMA.

                      Setting this object to enabled(1) enables the port
                      and exerts a BEGIN on the port's auto-partition
                      state machine.

                      (In effect, when a port is disabled, the value of
                      deprRptrPortAutoPartitionState for that port is frozen
                      until the port is next enabled.  When the port
                      becomes enabled, the deprRptrPortAutoPartitionState
                      becomes notAutoPartitioned(2), regardless of its
                      pre-disabling state.)"
			::= {deprRptrPortEntry 3}

deprRptrPortAutoPartitionState OBJECT-TYPE
			SYNTAX			INTEGER {
							autoPartitioned(1),
							notAutoPartitioned(2)
							}
			ACCESS			read-only
			STATUS			deprecated
			DESCRIPTION
                      "The autoPartitionState flag indicates whether the
                      port is currently partitioned by the repeater's
                      auto-partition protection.

                      The conditions that cause port partitioning are
                      specified in partition state machine in Sect. 9
                      [11]. They are not differentiated here."
			::= {deprRptrPortEntry 4}

deprRptrPortOperStatus 	OBJECT-TYPE
			SYNTAX			INTEGER {
							operational(1),
							notOperational(2),
							notPresent(3)
							}
			ACCESS			read-only
			STATUS			deprecated
			DESCRIPTION
                      "This object indicates the port's operational
                      state.  The notPresent(3) state indicates the port
                      is physically removed (note this may or may not be
                      possible depending on the type of port.) The
                      operational(1) state indicates that the port is
                      enabled (see deprRptrPortAdminStatus) and working, even
                      though it might be auto-partitioned (see
                      deprRptrPortAutoPartitionState)."
			::= {deprRptrPortEntry 5}

------------------------------------------------------------------------------------------
--											--
--			End of								--
--			Basic Group (deprecated)					--
--											--
------------------------------------------------------------------------------------------

------------------------------------------------------------------------------------------
--											--
--			Start of							--
--			Monitor Group (deprecated					--
--											--
------------------------------------------------------------------------------------------

--
--	Repeater Monitor Table
--

deprRptrMonitorTransmitCollisions OBJECT-TYPE
			SYNTAX			Counter
			ACCESS			read-only
			STATUS			deprecated
			DESCRIPTION
                     "This counter is incremented every time the
                      repeater state machine enters the TRANSMIT
                      COLLISION state from any state other than ONE PORT
                      LEFT (Ref: Fig 9-2) [11].

                      Note:  The approximate minimum time for counter
                      rollover is 16 hours."
			::= {deprRptrMonitorRptrInfo 1}

--
--	Group Monitor Table
--

deprRptrMonitorGroupTable	OBJECT-TYPE
			SYNTAX			SEQUENCE OF DeprRptrMonitorGroupEntry
			ACCESS			not-accessible
			STATUS			deprecated
			DESCRIPTION
                      "Table of performance and error statistics for the
                      groups."
			::= {deprRptrMonitorGroupInfo 1}

deprRptrMonitorGroupEntry	OBJECT-TYPE
			SYNTAX			DeprRptrMonitorGroupEntry
			ACCESS			not-accessible
			STATUS			deprecated
			DESCRIPTION
                      "An entry in the table, containing total
                      performance and error statistics for a single
                      group.  Regular retrieval of the information in
                      this table provides a means of tracking the
                      performance and health of the networked devices
                      attached to this group's ports.

                      The counters in this table are redundant in the
                      sense that they are the summations of information
                      already available through other objects.  However,
                      these sums provide a considerable optimization of
                      network management traffic over the otherwise
                      necessary retrieval of the individual counters
                      included in each sum."
			INDEX			{deprRptrMonitorGroupIndex}
			::= {deprRptrMonitorGroupTable 1}

			DeprRptrMonitorGroupEntry ::= SEQUENCE {
						deprRptrMonitorGroupIndex		INTEGER,
						deprRptrMonitorGroupTotalFrames		Counter,
						deprRptrMonitorGroupTotalOctets		Counter,
						deprRptrMonitorGroupTotalErrors		Counter
			}

deprRptrMonitorGroupIndex OBJECT-TYPE
			SYNTAX			INTEGER (1..1024)
			ACCESS			read-only
			STATUS			deprecated
			DESCRIPTION
                      "This object identifies the group within the
                      repeater for which this entry contains
                      information."
			::= {deprRptrMonitorGroupEntry 1}

deprRptrMonitorGroupTotalFrames	OBJECT-TYPE
			SYNTAX			Counter
			ACCESS			read-only
			STATUS			deprecated
			DESCRIPTION
                      "The total number of frames of valid frame length
                      that have been received on the ports in this
                      group.  This counter is the summation of the
                      values of the deprRptrMonitorPortReadableFrames
                      counters for all of the ports in the group.

                      This statistic provides one of the parameters
                      necessary for obtaining the packet error rate.
                      The approximate minimum time for rollover of this
                      counter is 80 hours."
			::= {deprRptrMonitorGroupEntry 2}

deprRptrMonitorGroupTotalOctets	OBJECT-TYPE
			SYNTAX			Counter
			ACCESS			read-only
			STATUS			deprecated
			DESCRIPTION
                      "The total number of octets contained in the valid
                      frames that have been received on the ports in
                      this group.  This counter is the summation of the
                      values of the deprRptrMonitorPortReadableOctets
                      counters for all of the ports in the group.

                      This statistic provides an indicator of the total
                      data transferred.  The approximate minimum time
                      for rollover of this counter is 58 minutes."
			::= {deprRptrMonitorGroupEntry 3}

deprRptrMonitorGroupTotalErrors	OBJECT-TYPE
			SYNTAX			Counter
			ACCESS			read-only
			STATUS			deprecated
			DESCRIPTION
                      "The total number of errors which have occurred on
                      all of the ports in this group.  This counter is
                      the summation of the values of the
                      deprRptrMonitorPortTotalErrors counters for all of the
                      ports in the group."
			::= {deprRptrMonitorGroupEntry 4}

--
--	Port Monitor Table
--

deprRptrMonitorPortTable	OBJECT-TYPE
			SYNTAX			SEQUENCE OF DeprRptrMonitorPortEntry
			ACCESS			not-accessible
			STATUS			deprecated
			DESCRIPTION
                      "Table of performance and error statistics for the
                      ports."
			::= {deprRptrMonitorPortInfo 1}

deprRptrMonitorPortEntry	OBJECT-TYPE
			SYNTAX			DeprRptrMonitorPortEntry
			ACCESS			not-accessible
			STATUS			deprecated
			DESCRIPTION
                      "An entry in the table, containing performance and
                      error statistics for a single port."
			INDEX			{deprRptrMonitorPortGroupIndex,deprRptrMonitorPortIndex}
			::= {deprRptrMonitorPortTable 1}

			DeprRptrMonitorPortEntry ::= SEQUENCE {
						deprRptrMonitorPortGroupIndex		INTEGER,
						deprRptrMonitorPortIndex		INTEGER,
						deprRptrMonitorPortReadableFrames	Counter,
						deprRptrMonitorPortReadableOctets	Counter,
						deprRptrMonitorPortFCSErrors		Counter,
						deprRptrMonitorPortAlignmentErrors	Counter,
						deprRptrMonitorPortFrameTooLongs	Counter,
						deprRptrMonitorPortShortEvents		Counter,
						deprRptrMonitorPortRunts		Counter,
						deprRptrMonitorPortCollisions		Counter,
						deprRptrMonitorPortLateEvents		Counter,
						deprRptrMonitorPortVeryLongEvents	Counter,
						deprRptrMonitorPortDataRateMismatches	Counter,
						deprRptrMonitorPortAutoPartitions	Counter,
						deprRptrMonitorPortTotalErrors		Counter
			}

deprRptrMonitorPortGroupIndex OBJECT-TYPE
			SYNTAX			INTEGER (1..16)
			ACCESS			read-only
			STATUS			deprecated
			DESCRIPTION
                      "This object identifies the group containing the
                      port for which this entry contains information."
			::= {deprRptrMonitorPortEntry 1}

deprRptrMonitorPortIndex	OBJECT-TYPE
			SYNTAX			INTEGER (1..1024)
			ACCESS			read-only
			STATUS			deprecated
			DESCRIPTION
                      "This object identifies the port within the group
                      for which this entry contains information."
			::= {deprRptrMonitorPortEntry 2}

deprRptrMonitorPortReadableFrames	OBJECT-TYPE
			SYNTAX			Counter
			ACCESS			read-only
			STATUS			deprecated
			DESCRIPTION
                      "This object is the number of frames of valid
                      frame length that have been received on this port.
                      This counter is incremented by one for each frame
                      received on this port whose OctetCount is greater
                      than or equal to minFrameSize and less than or
                      equal to maxFrameSize (Ref: IEEE 802.3 Std,
                      4.4.2.1) and for which the FCSError and
                      CollisionEvent signals are not asserted.

                      This statistic provides one of the parameters
                      necessary for obtaining the packet error rate.
                      The approximate minimum time for rollover of this
                      counter is 80 hours."
			::= {deprRptrMonitorPortEntry 3}

deprRptrMonitorPortReadableOctets	OBJECT-TYPE
			SYNTAX			Counter
			ACCESS			read-only
			STATUS			deprecated
			DESCRIPTION
                      "This object is the number of octets contained in
                      valid frames that have been received on this port.
                      This counter is incremented by OctetCount for each
                      frame received on this port which has been
                      determined to be a readable frame.

                      This statistic provides an indicator of the total
                      data transferred.  The approximate minimum time
                      for rollover of this counter is 58 minutes."
			::= {deprRptrMonitorPortEntry 4}

deprRptrMonitorPortFCSErrors OBJECT-TYPE
			SYNTAX			Counter
			ACCESS			read-only
			STATUS			deprecated
			DESCRIPTION
                      "This counter is incremented by one for each frame
                      received on this port with the FCSError signal
                      asserted and the FramingError and CollisionEvent
                      signals deasserted and whose OctetCount is greater
                      than or equal to minFrameSize and less than or
                      equal to maxFrameSize (Ref: 4.4.2.1, IEEE 802.3
                      Std).

                      The approximate minimum time for rollover of this
                      counter is 80 hours."
			::= {deprRptrMonitorPortEntry 5}

deprRptrMonitorPortAlignmentErrors OBJECT-TYPE
			SYNTAX			Counter
			ACCESS			read-only
			STATUS			deprecated
			DESCRIPTION
                      "This counter is incremented by one for each frame
                      received on this port with the FCSError and
                      FramingError signals asserted and CollisionEvent
                      signal deasserted and whose OctetCount is greater
                      than or equal to minFrameSize and less than or
                      equal to maxFrameSize (Ref: IEEE 802.3 Std,
                      4.4.2.1).  If deprRptrMonitorPortAlignmentErrors is
                      incremented then the deprRptrMonitorPortFCSErrors
                      Counter shall not be incremented for the same
                      frame.

                      The approximate minimum time for rollover of this
                      counter is 80 hours."
			::= {deprRptrMonitorPortEntry 6}

deprRptrMonitorPortFrameTooLongs	OBJECT-TYPE
			SYNTAX			Counter
			ACCESS			read-only
			STATUS			deprecated
			DESCRIPTION
                      "This counter is incremented by one for each frame
                      received on this port whose OctetCount is greater
                      than maxFrameSize (Ref: 4.4.2.1, IEEE 802.3 Std).
                      If deprRptrMonitorPortFrameTooLongs is incremented
                      then neither the deprRptrMonitorPortAlignmentErrors
                      nor the deprRptrMonitorPortFCSErrors counter shall be
                      incremented for the frame.

                      The approximate minimum time for rollover of this
                      counter is 61 days."
			::= {deprRptrMonitorPortEntry 7}

deprRptrMonitorPortShortEvents OBJECT-TYPE
			SYNTAX			Counter
			ACCESS			read-only
			STATUS			deprecated
			DESCRIPTION
                      "This counter is incremented by one for each
                      CarrierEvent on this port with ActivityDuration
                      less than ShortEventMaxTime.  ShortEventMaxTime is
                      greater than 74 bit times and less than 82 bit
                      times.  ShortEventMaxTime has tolerances included
                      to provide for circuit losses between a
                      conformance test point at the AUI and the
                      measurement point within the state machine.

                      Note:  shortEvents may indicate externally
                      generated noise hits which will cause the repeater
                      to transmit Runts to its other ports, or propagate
                      a collision (which may be late) back to the
                      transmitting DTE and damaged frames to the rest of
                      the network.

                      Implementors may wish to consider selecting the
                      ShortEventMaxTime towards the lower end of the
                      allowed tolerance range to accommodate bit losses
                      suffered through physical channel devices not
                      budgeted for within this standard.

                      The approximate minimum time for rollover of this
                      counter is 16 hours."
			::= {deprRptrMonitorPortEntry 8}

deprRptrMonitorPortRunts		OBJECT-TYPE
			SYNTAX			Counter
			ACCESS			read-only
			STATUS			deprecated
			DESCRIPTION
                      "This counter is incremented by one for each
                      CarrierEvent on this port that meets one of the
                      following two conditions.  Only one test need be
                      made.  a) The ActivityDuration is greater than
                      ShortEventMaxTime and less than ValidPacketMinTime
                      and the CollisionEvent signal is deasserted.  b)
                      The OctetCount is less than 64, the
                      ActivityDuration is greater than ShortEventMaxTime
                      and the CollisionEvent signal is deasserted.
                      ValidPacketMinTime is greater than or equal to 552
                      bit times and less than 565 bit times.

                      An event whose length is greater than 74 bit times
                      but less than 82 bit times shall increment either
                      the shortEvents counter or the runts counter but
                      not both.  A CarrierEvent greater than or equal to
                      552 bit times but less than 565 bit times may or
                      may not be counted as a runt.

                      ValidPacketMinTime has tolerances included to
                      provide for circuit losses between a conformance
                      test point at the AUI and the measurement point
                      within the state machine.

                      Runts usually indicate collision fragments, a
                      normal network event.  In certain situations
                      associated with large diameter networks a
                      percentage of runts may exceed ValidPacketMinTime.

                      The approximate minimum time for rollover of this
                      counter is 16 hours."
			::= {deprRptrMonitorPortEntry 9}

deprRptrMonitorPortCollisions 	OBJECT-TYPE
			SYNTAX			Counter
			ACCESS			read-only
			STATUS			deprecated
			DESCRIPTION
                      "This counter is incremented by one for any
                      CarrierEvent signal on any port for which the
                      CollisionEvent signal on this port is asserted.

                      The approximate minimum time for rollover of this
                      counter is 16 hours."
			::= {deprRptrMonitorPortEntry 10}

deprRptrMonitorPortLateEvents OBJECT-TYPE
			SYNTAX			Counter
			ACCESS			read-only
			STATUS			deprecated
			DESCRIPTION
                      "This counter is incremented by one for each
                      CarrierEvent on this port in which the CollIn(X)
                      variable transitions to the value SQE (Ref:
                      9.6.6.2, IEEE 802.3 Std) while the
                      ActivityDuration is greater than the
                      LateEventThreshold.  Such a CarrierEvent is
                      counted twice, as both a collision and as a
                      lateEvent.

                      The LateEventThreshold is greater than 480 bit
                      times and less than 565 bit times.
                      LateEventThreshold has tolerances included to
                      permit an implementation to build a single
                      threshold to serve as both the LateEventThreshold
                      and ValidPacketMinTime threshold.

                      The approximate minimum time for rollover of this
                      counter is 81 hours."
			::= {deprRptrMonitorPortEntry 11}

deprRptrMonitorPortVeryLongEvents	OBJECT-TYPE
			SYNTAX			Counter
			ACCESS			read-only
			STATUS			deprecated
			DESCRIPTION
                      "This counter is incremented by one for each
                      CarrierEvent on this port whose ActivityDuration
                      is greater than the MAU Jabber Lockup Protection
                      timer TW3 (Ref: 9.6.1 & 9.6.5, IEEE 802.3 Std).
                      Other counters may be incremented as appropriate."
			::= {deprRptrMonitorPortEntry 12}

deprRptrMonitorPortDataRateMismatches OBJECT-TYPE
			SYNTAX			Counter
			ACCESS			read-only
			STATUS			deprecated
			DESCRIPTION
                      "This counter is incremented by one for each frame
                      received on this port that meets all of the
                      following conditions:  a) The CollisionEvent
                      signal is not asserted.  b) The ActivityDuration
                      is greater than ValidPacketMinTime.  c) The
                      frequency (data rate) is detectably mismatched
                      from the local transmit frequency.  The exact
                      degree of mismatch is vendor specific and is to be
                      defined by the vendor for conformance testing.

                      When this event occurs, other counters whose
                      increment conditions were satisfied may or may not
                      also be incremented, at the implementor's
                      discretion.  Whether or not the repeater was able
                      to maintain data integrity is beyond the scope of
                      this standard."
			::= {deprRptrMonitorPortEntry 13}

deprRptrMonitorPortAutoPartitions OBJECT-TYPE
			SYNTAX			Counter
			ACCESS			read-only
			STATUS			deprecated
			DESCRIPTION
                      "This counter is incremented by one for each time
                      the repeater has automatically partitioned this
                      port.  The conditions that cause port partitioning
                      are specified in the partition state machine in
                      Section 9 [IEEE 802.3 Std].  They are not
                      differentiated here."
			::= {deprRptrMonitorPortEntry 14}

deprRptrMonitorPortTotalErrors OBJECT-TYPE
			SYNTAX			Counter
			ACCESS			read-only
			STATUS			deprecated
			DESCRIPTION
                      "The total number of errors which have occurred on
                      this port.  This counter is the summation of the
                      values of other error counters (for the same
                      port), namely:

                          deprRptrMonitorPortFCSErrors,
                          deprRptrMonitorPortAlignmentErrors,
                          deprRptrMonitorPortFrameTooLongs,
                          deprRptrMonitorPortShortEvents,
                          deprRptrMonitorPortLateEvents,
                          deprRptrMonitorPortVeryLongEvents, and
                          deprRptrMonitorPortDataRateMismatches.

                      This counter is redundant in the sense that it is
                      the summation of information already available
                      through other objects.  However, it is included
                      specifically because the regular retrieval of this
                      object as a means of tracking the health of a port
                      provides a considerable optimization of network
                      management traffic over the otherwise necessary
                      retrieval of the summed counters."
			::= {deprRptrMonitorPortEntry 15}

------------------------------------------------------------------------------------------
--											--
--			End of								--
--			Monitor Group (deprecated)					--
--											--
------------------------------------------------------------------------------------------

------------------------------------------------------------------------------------------
--											--
--			Start of							--
--			Address Tracking Group (deprecated)				--
--											--
------------------------------------------------------------------------------------------

--
--	Repeater Address Tracking Table (deprecated)
--

--
--	Group Address Tracking Table (deprecated)
--

--
--	Port Address Tracking Table (deprecated)

deprRptrAddrTrackTable	OBJECT-TYPE
			SYNTAX			SEQUENCE OF DeprRptrAddrTrackEntry
			ACCESS			not-accessible
			STATUS			deprecated
			DESCRIPTION
                      "Table of address mapping information about the
                      ports."
			::= {deprRptrAddrTrackPortInfo 1}

deprRptrAddrTrackEntry	OBJECT-TYPE
			SYNTAX			DeprRptrAddrTrackEntry
			ACCESS			not-accessible
			STATUS			deprecated
			DESCRIPTION
                      "An entry in the table, containing address mapping
                      information about a single port."
			INDEX			{deprRptrAddrTrackGroupIndex,deprRptrAddrTrackPortIndex}
			::= {deprRptrAddrTrackTable 1}

			DeprRptrAddrTrackEntry ::= SEQUENCE {
						deprRptrAddrTrackGroupIndex		INTEGER,
						deprRptrAddrTrackPortIndex		INTEGER,
						deprRptrAddrTrackLastSourceAddress	PhysAddress,
						deprRptrAddrTrackSourceAddrChanges	Counter
			}

deprRptrAddrTrackGroupIndex	OBJECT-TYPE
			SYNTAX			INTEGER (1..16)
			ACCESS			read-only
			STATUS			deprecated
			DESCRIPTION
                      "This object identifies the group containing the
                      port for which this entry contains information."
			::= {deprRptrAddrTrackEntry 1}

deprRptrAddrTrackPortIndex	OBJECT-TYPE
			SYNTAX			INTEGER (1..1024)
			ACCESS			read-only
			STATUS			deprecated
			DESCRIPTION
                      "This object identifies the port within the group
                      for which this entry contains information."
			::= {deprRptrAddrTrackEntry 2}

deprRptrAddrTrackLastSourceAddress OBJECT-TYPE
			SYNTAX			PhysAddress
			ACCESS			read-only
			STATUS			deprecated
			DESCRIPTION
                      "This object is the SourceAddress of the last
                      readable frame (i.e., counted by
                      deprRptrMonitorPortReadableFrames) received by this
                      port."
			::= {deprRptrAddrTrackEntry 3}

deprRptrAddrTrackSourceAddrChanges OBJECT-TYPE
			SYNTAX			Counter
			ACCESS			read-only
			STATUS			deprecated
			DESCRIPTION
                      "This counter is incremented by one for each time
                      that the deprRptrAddrTrackLastSourceAddress attribute
                      for this port has changed.

                      This may indicate whether a link is connected to a
                      single DTE or another multi-user segment.

                      The approximate minimum time for rollover of this
                      counter is 81 hours."
			::= {deprRptrAddrTrackEntry 4}

------------------------------------------------------------------------------------------
--											--
--			End of								--
--			Address Tracking Group (deprecated)				--
--											--
------------------------------------------------------------------------------------------

------------------------------------------------------------------------------------------
--											--
--			Start of 							--
--			Trap Definitions						--
--			These traps will no longer be generated.			--
--			Reference replacements in rfc1368				--
--											--
------------------------------------------------------------------------------------------

deprRptrHealth	TRAP-TYPE
		ENTERPRISE		a3Com
		VARIABLES		{
					 deprRptrOperStatus
					}
		DESCRIPTION
                      "The deprRptrHealth trap conveys information related
                      to the operational state of the repeater. This
                      trap is sent only when the oper status of the
                      repeater changes.

                      The deprRptrHealth trap must contain the deprRptrOperStatus
                      variable. The agent may optionally include the
                      deprRptrHealthText variable in the varBind list.  See
                      the deprRptrOperStatus and deprRptrHealthText objects for
                      descriptions of the information that is sent.

                      The agent must throttle the generation of
                      consecutive deprRptrHealth traps so that there is at
                      least a five-second gap between them."
		::=			1

deprRptrGroupChange	TRAP-TYPE
		ENTERPRISE		a3Com
		VARIABLES		{
					 deprRptrGroupIndex
					}
		DESCRIPTION
                      "This trap is sent when a change occurs in the
                      group structure of a repeater. This occurs only
                      when a group is logically removed from or added to
                      a repeater. The varBind list contains the
                      identifier of the group that was removed or added.

                      The agent must throttle the generation of
                      consecutive deprRptrGroupChange traps for the same
                      group so that there is at least a five-second gap
                      between them."
		::=			2

deprRptrResetEvent	TRAP-TYPE
		ENTERPRISE		a3Com
		VARIABLES		{
					 deprRptrOperStatus
					}
		DESCRIPTION
                      "The deprRptrReset trap conveys information related to
                      the operational state of the repeater. This trap
                      is sent on completion of a repeater reset action.
                      A repeater reset action is defined as an a
                      transition to the START state of Fig 9-2 in
                      section 9 [11], when triggered by a management
                      command (e.g., an SNMP Set on the deprRptrReset
                      object).

                      The agent must throttle the generation of
                      consecutive deprRptrReset traps so that there is at
                      least a five-second gap between them.

                      The deprRptrReset trap is not sent when the agent
                      restarts and sends an SNMP coldStart or warmStart
                      trap. However, it is recommended that a repeater
                      agent send the deprRptrHealth variables as optional
                      variables with its coldStart and warmStart trap
                      PDUs.

                      The deprRptrOperStatus variable must be included in the
                      varbind list sent with this trap.  The agent may
                      optionally include the deprRptrHealthText variable as
                      well."
		::=			3

------------------------------------------------------------------------------------------
--											--
--			End of 								--
--			Trap Definitions						--
--			These traps will no longer be generated.			--
--			Reference replacements in rfc1368				--
--											--
------------------------------------------------------------------------------------------

deprSnmpDot3RpMauMgt OBJECT IDENTIFIER ::= { linkBuilder10BTi-mib 5 }

------------------------------------------------------------------------------------------
--											--
--		the only group in the SNMP Repeater MAU Mib				--
--		the rpMauBasicGroup is deprecated					--
--											--
------------------------------------------------------------------------------------------

deprRpMauBasicGroup	OBJECT IDENTIFIER ::= { deprSnmpDot3RpMauMgt 1 }

--
-- The Basic Repeater MAU Table
--

deprRpMauTable	OBJECT-TYPE
		SYNTAX			SEQUENCE OF DeprRpMauEntry
		ACCESS			not-accessible
		STATUS			deprecated
		DESCRIPTION
		"Table of descriptive and status information about
		 the groups of ports."
		::= { deprRpMauBasicGroup 1 }

deprRpMauEntry	OBJECT-TYPE
		SYNTAX			DeprRpMauEntry
		ACCESS			not-accessible
		STATUS			deprecated
		DESCRIPTION
		"An entry in the table, containing information
		 about a single group of ports."
		INDEX  			{ deprRpMauGroupIndex, deprRpMauPortIndex,
					  deprRpMauIndex }
		::= { deprRpMauTable 1 }

          DeprRpMauEntry ::= SEQUENCE {
             		     		deprRpMauGroupIndex		INTEGER,
                 		 	deprRpMauPortIndex		INTEGER,
                  			deprRpMauIndex			INTEGER,
                  			deprRpMauType			INTEGER,
                  			deprRpMauAdminState		INTEGER,
                  			deprRpMauMediaAvailable		INTEGER,
                  			deprRpMauLostMedias		Counter,
                  			deprRpMauJabberState		INTEGER,
                  			deprRpMauJabbers		Counter
              }

deprRpMauGroupIndex	OBJECT-TYPE
		SYNTAX			INTEGER (1..1024)
		ACCESS			read-only
		STATUS			deprecated
		DESCRIPTION
		"This variable uniquely identifies the repeater
		 group that contains the port to which is connected
		 the MAU for which this entry contains
		 information."
		::= { deprRpMauEntry 1 }

deprRpMauPortIndex	OBJECT-TYPE
		SYNTAX			INTEGER (1..1024)
		ACCESS			read-only
		STATUS			deprecated
		DESCRIPTION
		"This variable uniquely identifies the repeater
		 port to which is connected the MAU for which this
		 entry contains information."
		::= { deprRpMauEntry 2 }

deprRpMauIndex	OBJECT-TYPE
		SYNTAX			INTEGER (1..1024)
		ACCESS			read-only
		STATUS			deprecated
		DESCRIPTION
		"This variable uniquely identifies the MAU for
		which this entry contains information."
		::= { deprRpMauEntry 3 }

deprRpMauType	OBJECT-TYPE
		SYNTAX			INTEGER {
						other(1),     -- undefined
						unknown(2),   -- initializing,
					       		       -- true state not yet known
						aui(7),       -- no internal MAU,
					      		        -- view from AUI
						tenbase5(8),   -- thick coax MAU per sec 8
						foirl(9),     -- FOIRL MAU per sec 9.9
						tenbase2(10),  -- thin coax MAU per sec 10
						tenbaseT(14),  -- UTP MAU per sec 14
						tenbaseFP(16), -- passive fiber MAU per sec 16
						tenbaseFB(17), -- sync fiber MAU per 17
						tenbaseFL(18)  -- async fiber MAU per sec 18
						}
		ACCESS			read-only
		STATUS			deprecated
		DESCRIPTION
		"A value that identifies the 10 Mb/s baseband MAU
		 type. The enumeration of the type is such that the
		 value matches the section number of the IEEE 802.3
		 standard that specifies the particular MAU."
		::= { deprRpMauEntry 4 }

deprRpMauAdminState	OBJECT-TYPE
		SYNTAX			INTEGER {
						other(1),        -- undefined
						unknown(2),      -- initalizing,
						                 -- true state not yet known
						operational(3),  -- powered and connected
						standby(4),      -- inactive but on
						shutdown(5),     -- similar to power down
						reset(6)         -- write-only to reset mau
						}
		ACCESS			read-write
		STATUS			deprecated
		DESCRIPTION
		"The administrative state of the MAU.  This object
		may be implemented as a read-only object by those
		agents and MAUs that do not implement software
		control of the administrative state.

		A MAU in the operational(3) state is fully
		functional, operates, and passes signals to its
		attached DTE or repeater port in accordance to its
		specification.

		A MAU in standby(4) state forces DI and CI and the
		media transmitter to idle.  Standby(4) mode only
		applies to link type MAUs.  The state of
		mauMediaAvailable is unaffected.

		A MAU in shutdown(5) state assumes the same
		condition on DI, CI, and the media transmitter as
		if it were powered down.  The MAU may return
		other(1) state for the mauJabber and
		mauMediaAvailable objects when it is in this
		state.  For an AUI, this state will remove power
		from the AUI.

		Setting this variable to the value reset(6) resets
		the MAU in the same manner as a power-off, power-
		on cycle would.

		Setting this variable to the value operational(3),
		standby(4), or shutdown(5) causes the MAU to
		assume the respective state except that setting a
		mixing-type MAU or an AUI to standby(4) will cause
		the MAU to enter the shutdown state."
		::= { deprRpMauEntry 5 }

deprRpMauMediaAvailable OBJECT-TYPE
		SYNTAX			INTEGER {
						other(1),         -- undefined

						unknown(2),       -- initializing,
						                  -- true state not yet known
						present(3),       -- link or light normal,
						                  -- loopback normal
						notPresent(4),    -- link loss or low light,
						                  -- no loopback
						remoteFault(5),   -- remote fault,
						                  -- applies only to 10BASE-FB
						invalidSignal(6)  -- invalid signal,
						                  -- applies only to 10BASE-FB
						}
		ACCESS			read-only
		STATUS			deprecated
		DESCRIPTION
		"If the MAU is a link or fiber type (FOIRL,
		10BASE-T, 10BASE-F) then this is equivalent to the
		link integrity/low light state. For an AUI or coax
		MAU this indicates whether or not loopback is
		detected on the DI circuit. The value of this
		attribute persists between packets for MAU types
		AUI, 10BASE5, 10BASE2, and 10BASE-FP.

		NOTE:  IEEE 802.3 modified the following
		descriptive text at their meeting the week of
		3/9/92.  New text will be provided at the San
		Diego IETF plenary.

		At power-up or following a reset, the value of
		this attribute will be unknown for AUI, coax, and
		10BASE-FP MAUs. For these MAUs loopback will be
		tested on each transmission during which no
		collision is detected. If DI receives input within
		startUpDelay of the start of output on DO,
		loopback will be detected. The value of
		startUpDelay shall be between 15 and 25 BT (bit
		times). Transition form input to output_idle on DI
		while output is present on DO may also be detected
		on loopback. The value of this attribute will only
		change during non-collided transmissions for AUI,
		coax, and 10BASE-FP MAUs."
		::= { deprRpMauEntry 6 }

deprRpMauLostMedias	OBJECT-TYPE
		SYNTAX			Counter
		ACCESS			read-only
		STATUS			deprecated
		DESCRIPTION
		"A count of the number of times that
		deprRpMauMediaAvailable for this MAU instance leaves
		the state available(3).

		Implementation of this object is mandatory for MAU
		instances with deprRpMauType of AUI(7).  It is
		recommended for all MAU types."
		::= { deprRpMauEntry 7 }

deprRpMauJabberState OBJECT-TYPE
		SYNTAX			INTEGER {
						other(1),     -- undefined
						unknown(2),   -- initializing,
						              -- true state not yet known
						noJabber(3),  -- state is normal
						jabbering(4)  -- MAU is jabbering
						}
		ACCESS			read-only
		STATUS			deprecated
		DESCRIPTION
		"If the MAU is in jabber state the attribute is
		set to the jabbering(4) value. This object returns
		the value other(1) for MAU type AUI."
		::= { deprRpMauEntry 8 }

deprRpMauJabbers	OBJECT-TYPE
		SYNTAX			Counter
		ACCESS			read-only
		STATUS			deprecated
		DESCRIPTION
		"A count of the number of times that
		deprRpMauJabberState for this MAU instance enters the
		state jabbering(4)."
		::= { deprRpMauEntry 9 }

------------------------------------------------------------------------------------------
--											--
--				Trap definition						--
--											--
------------------------------------------------------------------------------------------

deprRpMauJabberTrap	TRAP-TYPE
		ENTERPRISE	a3Com
		VARIABLES	{
				deprRptrOperStatus
				}
		DESCRIPTION
                      "This trap is sent whenever a managed MAU enters
                      the jabber state.

                      The agent must throttle the generation of
                      consecutive deprRpMauJabberTraps so that there is at
                      least a five-second gap between them."
		::=		24

-- ----------------------------------------
--
-- Fault Table
--
-- ----------------------------------------

faultModifiedFlag	OBJECT-TYPE
			SYNTAX			INTEGER
							{
							clean-read	(1),
							modified	(2)
							}
			ACCESS			read-write
			STATUS			mandatory
			DESCRIPTION
				"In order to ensure a clean read of the Fault table this flag
				should be set to clean_read when commencing to read the table and should
				be examined after reading the entire table. If still set to clean_read
				then the table read is okay, if not the table should be
				re-read as it has been modified during the read process."
			::= { fault 1 }

faultTable		OBJECT-TYPE
			SYNTAX	SEQUENCE OF 	FaultEntry
			ACCESS			not-accessible
			STATUS			mandatory
			DESCRIPTION
				"The Fault Table."
			::= { fault 2 }

faultEntry		OBJECT-TYPE
			SYNTAX			FaultEntry
			ACCESS			not-accessible
			STATUS			mandatory
			DESCRIPTION
				"Information relating to a single fault."
			INDEX			{ faultIndex }
			::= { faultTable 1 }

			FaultEntry ::= SEQUENCE {
						faultIndex		INTEGER,
						faultErrorNumber	INTEGER,
						faultTimeStamp	TimeTicks,
						faultRestartCount	INTEGER
						     }

faultIndex		OBJECT-TYPE
			SYNTAX			INTEGER
			ACCESS			read-only
			STATUS			mandatory
			DESCRIPTION
				"The index into the Fault table.  The initial read from the
				table should be read as the next, from an index of 0;
				subsequent reads should read the next from the index returned
				by the previous read."
			::= { faultEntry 1 }

faultErrorNumber	OBJECT-TYPE
			SYNTAX			INTEGER
			ACCESS			read-only
			STATUS			mandatory
			DESCRIPTION
				"This error number for this fault log entry."
			::= { faultEntry 2 }

faultTimeStamp	OBJECT-TYPE
			SYNTAX			TimeTicks
			ACCESS			read-only
			STATUS			mandatory
			DESCRIPTION
				"The time since startup, in milliseconds, when the fault
				occurred."
			::= { faultEntry 3 }

faultRestartCount	OBJECT-TYPE
			SYNTAX			INTEGER
			ACCESS			read-only
			STATUS			mandatory
			DESCRIPTION
				"The number of restarts at time of fault."
			::= { faultEntry 4 }
--------------------------------------------------------------------------
--									--
--				Start of				--
--		    PDDRM Generic Multi-Repeater MIB.			--
--									--
-- This MIB duplicates all the relevant information from the standard
-- IETF repeater MIB. Some is missing because it is not useful to
-- Isoview or a generic manager.
--------------------------------------------------------------------------

mrmBasicPackage			OBJECT IDENTIFIER ::= { multiRepeater 1}
mrmMonitorPackage		OBJECT IDENTIFIER ::= { multiRepeater 2}

mrmBasCardPackage		OBJECT IDENTIFIER ::= { mrmBasicPackage 1 }
mrmBasPortPackage		OBJECT IDENTIFIER ::= { mrmBasicPackage 2 }

mrmMonRepeaterPackage		OBJECT IDENTIFIER ::= { mrmMonitorPackage 1}
mrmMonCardPackage		OBJECT IDENTIFIER ::= { mrmMonitorPackage 2}
mrmMonPortPackage		OBJECT IDENTIFIER ::= { mrmMonitorPackage 3}
mrmMonDummyPackage		OBJECT IDENTIFIER ::= { mrmMonitorPackage 4}
mrmMonRepeaterSmartPackage	OBJECT IDENTIFIER ::= { mrmMonitorPackage 5}
mrmMonCardSmartPackage		OBJECT IDENTIFIER ::= { mrmMonitorPackage 6}
mrmMonPortSmartPackage		OBJECT IDENTIFIER ::= { mrmMonitorPackage 7}

--------------------------------------------------------------------------
--									--
--				Start of				--
--			       Basic Group				--
--									--
--------------------------------------------------------------------------

--
--	MRM Basic Group Table
--

mrmCardTable OBJECT-TYPE
	SYNTAX    		SEQUENCE OF MrmCardEntry
	ACCESS    		not-accessible
	STATUS    		mandatory
	DESCRIPTION "
Table of descriptive and status information about the groups of ports."
	::= { mrmBasCardPackage 1 }

mrmCardEntry 			OBJECT-TYPE
	SYNTAX    		MrmCardEntry
	ACCESS    		not-accessible
	STATUS    		mandatory
	DESCRIPTION "
An entry in the table, containing information about a single group of ports."
	INDEX    		{ mrmCardServiceId, mrmCardIndex }
	::= { mrmCardTable 1 }

	MrmCardEntry ::=
	SEQUENCE {
		mrmCardServiceId		INTEGER,
		mrmCardIndex			INTEGER,
		mrmCardPortCapacity		INTEGER,
		mrmCardTest			INTEGER,
		mrmCardDOBPorts			INTEGER,
		mrmCardMDIenable                INTEGER
	}

mrmCardServiceId OBJECT-TYPE
	SYNTAX    		INTEGER
	ACCESS    		read-only
	STATUS    		mandatory
	DESCRIPTION "
This identifies one of the repeaters within the chassis as the target
of a request."
 	::= { mrmCardEntry 1 }

mrmCardIndex 			OBJECT-TYPE
	SYNTAX    		INTEGER
	ACCESS    		read-only
	STATUS    		mandatory
	DESCRIPTION "
This object identifies the card within the repeater for which this
entry contains information."
 	::= { mrmCardEntry 2 }

mrmCardPortCapacity 		OBJECT-TYPE
	SYNTAX    		INTEGER
	ACCESS    		read-only
	STATUS    		mandatory
	DESCRIPTION "
The mrmCardPortCapacity is the number of ports that can be contained
within the group.  Valid range is 1-1024.  Within each group, the
ports are uniquely numbered in the range from 1 to
mrmCardPortCapacity.

Note: In practice, this will generally be the number of ports on a
module, card, or board, and the port numbers will correspond to
numbers marked on the physical embodiment."
	::= { mrmCardEntry 3 }

mrmCardTest 			OBJECT-TYPE
	SYNTAX 			INTEGER {
					noTest(1),
					test(2),
					testing(3),
					passed(4),
					failed(5)
				}
	ACCESS    		read-write
	STATUS    		mandatory
	DESCRIPTION "
An object that allows the user to test the operation of a card.
Writing test(2) to this object forces the card to perform a disruptive
test to determine if the card is functioning properly. Reading this
object while the card is under test return the value testing(3). When
the test is completed, reading this value will return either passed(4)
or failed(5)."
	::= { mrmCardEntry 4 }

mrmCardDOBPorts	OBJECT-TYPE
	SYNTAX		INTEGER
	ACCESS		read-only
	STATUS		mandatory
	DESCRIPTION "
MSH Repeater Cards have the ability to disable ports at power up or reset.
Ports configured in this way are useful for configuring resilient links
because they prevent loops in the network from occurring at startup. The
disable on boot feature is determined according to a hardware strap which
cannot be changed via software. This parameter is a mask containing a single
bit for each port on the card. Port 1 is represented by bit 0 and so-on. If
a bit representing a particular port is 0 this port boots up disabled. If
the bit is a 1 the port boots up enabled.

This parameter allows the state of these parameters to be rapidly determined
by a network management application."
	::= { mrmCardEntry 5 }

mrmCardMDIenable OBJECT-TYPE
	SYNTAX		INTEGER {
		unknown(1),
		mdiDisabled(2),
		mdiEnabled(3),
		notApplicable(4)
	}
	ACCESS		read-only
	STATUS		mandatory
	DESCRIPTION "
	10Base-T line cards are normally configured (mdi_disabled(2)) to link
	to an external network device ( internal crossover ).
	Port 1 may be configured ( mdi_enabled(3) ) to link to another
	10Base-T line card ( with no internal crossover ).
	This parameter allows the configuration to be determined.
	Note ECS line cards show unknown(1) since the configuration cannot
	be accessed via the management interface."
	::= { mrmCardEntry 6 }

--
--	MRM Basic Port Table
--

mrmPortTable OBJECT-TYPE
	SYNTAX    SEQUENCE OF MrmPortEntry
	ACCESS    not-accessible
	STATUS    mandatory
	DESCRIPTION "
Table of descriptive and status information about the ports."
	::= { mrmBasPortPackage 1 }

mrmPortEntry OBJECT-TYPE
	SYNTAX    MrmPortEntry
	ACCESS    not-accessible
	STATUS    mandatory
	DESCRIPTION "
An entry in the table, containing information about a single port."

	INDEX    { mrmPortServiceId, mrmPortCardIndex, mrmPortIndex }
	::= { mrmPortTable 1 }

	MrmPortEntry ::=
	SEQUENCE {
		mrmPortServiceId		INTEGER,
		mrmPortCardIndex		INTEGER,
		mrmPortIndex			INTEGER,
		mrmPortInterfaceType		INTEGER,
		mrmPortConnectorType		INTEGER,
		mrmPortAdminStatus		INTEGER,
		mrmPortAutoPartitionState	INTEGER,
		mrmPortLinkState		INTEGER,
		mrmPortBootState		INTEGER,
		mrmPortESTFilter		INTEGER,
		mrmPortPartitionEvent		INTEGER,
		mrmPortLinkStateEvent		INTEGER,
		mrmPortSecurityAvailable	INTEGER,
		mrmPortLinkPulse		INTEGER,
		mrmPortModule			INTEGER,
		mrmPortDUDAction		INTEGER,
		mrmPortFunction			INTEGER
	}

mrmPortServiceId OBJECT-TYPE
	SYNTAX    INTEGER
	ACCESS    read-only
	STATUS    mandatory
	DESCRIPTION "
This object identifies the repeater which this entry contains information."
              ::= { mrmPortEntry 1 }

mrmPortCardIndex OBJECT-TYPE
	SYNTAX    INTEGER
	ACCESS    read-only
	STATUS    mandatory
	DESCRIPTION "
This object identifies the group containing the port for which this
entry contains information."
              ::= { mrmPortEntry 2 }

mrmPortIndex OBJECT-TYPE
	SYNTAX    INTEGER
	ACCESS    read-only
	STATUS    mandatory
	DESCRIPTION "
This object identifies the port within the group for which this entry
contains information.  This value can never be greater than
mrmCardPortCapacity for the associated group."
	REFERENCE
	"Reference IEEE 802.3 Rptr Mgt, 19.2.6.2,aPortID."
 	::= { mrmPortEntry 3 }

mrmPortInterfaceType OBJECT-TYPE
	SYNTAX	INTEGER {
		unknown(1),
		maleAUI(2),
		femaleAUI(3),
		thinCoax(4),
		twistedPair(5),
		unshieldedTP(6),
		fiber(7)
	}
	ACCESS	read-only
	STATUS	mandatory
	DESCRIPTION "
This object specifies the type of electrical interface made available at the
interface to the card for this port. The interface does not necessarily
specify what the actual media to end station is."
	::= { mrmPortEntry 4 }

mrmPortConnectorType OBJECT-TYPE
	SYNTAX	INTEGER {
		unknown(1),
		rj45(2),
		telco(3),
		st(4),
		sma(5),
		dtype-15(6),
		bnc(7)
	}
	ACCESS	read-only
	STATUS	mandatory
	DESCRIPTION "
This specifies the type of the physical connector through which one
would attach to this card. This is distinct from the media type. For
example UTP may be connected to the port via either an RJ45 or a Telco
connector."
	::= { mrmPortEntry 5 }

mrmPortAdminStatus OBJECT-TYPE
	SYNTAX	INTEGER {
		enabled(1),
		disabled(2)
	}
	ACCESS    read-write
	STATUS    mandatory
	DESCRIPTION "
Setting this object to disabled(2) disables the port.  A disabled port
neither transmits nor receives.  Once disabled, a port must be
explicitly enabled to restore operation.  A port which is disabled
when power is lost or when a reset is exerted shall remain disabled
when normal operation resumes.

The admin status takes precedence over auto- partition and
functionally operates between the auto-partition mechanism and the
AUI/PMA.

Setting this object to enabled(1) enables the port and exerts a BEGIN
on the port's auto-partition state machine.

In effect, when a port is disabled, the value of
mrmPortAutoPartitionState for that port is frozen until the port is
next enabled.  When the port becomes enabled, the
mrmPortAutoPartitionState becomes notAutoPartitioned(2), regardless
of its pre-disabling state.)"
	::= { mrmPortEntry 6 }

mrmPortAutoPartitionState OBJECT-TYPE
	SYNTAX    INTEGER {
		partitioned(1),
		unpartitioned(2)
	}
	ACCESS    read-only
	STATUS    mandatory
	DESCRIPTION "
The autoPartitionState flag indicates whether the port is currently
partitioned by the repeater's auto-partition protection.

The conditions that cause port partitioning are specified in partition
state machine in Section 9 IEEE 802.3 Std].  They are not
differentiated here."
	REFERENCE
	"Reference IEEE 802.3 Rptr Mgt, 19.2.6.2, aAutoPartitionState."
	::= { mrmPortEntry 7 }

mrmPortLinkState  OBJECT-TYPE
	SYNTAX INTEGER {
		present(1),
		absent(2)
	}
	ACCESS    read-only
	STATUS    mandatory
	DESCRIPTION "
This object reflects the presence or absence of signal on this port. The
signal may be either light in the case of fiber, or general link
present in the case of copper. The value of this parameter is correct
regardless of the state the admin state or the partition state."
	::= { mrmPortEntry 8 }

mrmPortBootState OBJECT-TYPE
	SYNTAX INTEGER {
		disable (1),
		enable (2)
	}
	ACCESS			read-only
	STATUS			mandatory
	DESCRIPTION "
A repeater port may be enabled or disabled after a reset. This parameter
indicates the default for this port."
	::= { mrmPortEntry 9 }

mrmPortESTFilter	 OBJECT-TYPE
	SYNTAX	INTEGER {
		forwardMAC		(1),
		forwardIP		(2),
		forwardAll		(127),
		forwardNone		(128)
	}
	ACCESS			read-write
	STATUS			mandatory
	DESCRIPTION "
This attribute determines whether and which address information is
extracted from packets received on a port  and forwarded to the end
station database. It is recommended that this attribute be disabled
for inter-repeater links to prevent the database being filled with
remote information. To disable this feature for all address types
write the value forwardNone (128) to this variable."
		::= {mrmPortEntry 10}

mrmPortPartitionEvent OBJECT-TYPE
	SYNTAX	INTEGER {
		enabled(1),
		disabled(2)
	}
	ACCESS    read-write
	STATUS    mandatory
	DESCRIPTION "Specifies whether a trap should be sent if the port
partition state changes."
	::= { mrmPortEntry 11 }

mrmPortLinkStateEvent OBJECT-TYPE
	SYNTAX	INTEGER {
		enabled(1),
		disabled(2)
	}
	ACCESS    read-write
	STATUS    mandatory
	DESCRIPTION "Specifies whether a trap should be sent if the link
state changes."
	::= { mrmPortEntry 12 }

mrmPortSecurityAvailable OBJECT-TYPE
	SYNTAX	INTEGER {
		available(1),
		notAvailable(2)
	}
	ACCESS    read-only
	STATUS    mandatory
	DESCRIPTION "Specifies whether security is an available feature on
this port. Only ports that have this feature available can have an entry in
the repeater security table."
	::= { mrmPortEntry 13 }

mrmPortLinkPulse OBJECT-TYPE
	SYNTAX INTEGER {
		enabled		(1),
		disabled	(2),
		notApplicable	(3)
	}
	ACCESS			read-write
	STATUS			mandatory
	DESCRIPTION "
This attribute determines if link pulse generating and monitoring is enabled
or disabled for a 10BaseT port. The attribute may take
the values of enabled (standard) or disabled (non standard)."
	::= { mrmPortEntry 14 }

mrmPortModule OBJECT-TYPE
	SYNTAX INTEGER {
		unknown		(1),
		modularPort	(2),
		notModularPort	(3)
	}
	ACCESS			read-only
	STATUS			mandatory
	DESCRIPTION "
	This attribute indicates whether the port is a modular port or not."
	::= { mrmPortEntry 15 }

mrmPortDUDAction   OBJECT-TYPE
        SYNTAX                  INTEGER {
                                         noAction        (1),
                                         notify          (2),
                                         disconnect      (3)
                                         }
        ACCESS                  read-write
        STATUS                  mandatory
        DESCRIPTION     "
        DUD Action for this port.
        "
        ::= {mrmPortEntry 16}

mrmPortFunction OBJECT-TYPE
	SYNTAX	INTEGER {
		unknown(1),
		repeater(2),
		bridge(3)
	}
	ACCESS    read-only
	STATUS    mandatory
	DESCRIPTION "
	This atribute indicates the function of the port."
	::= { mrmPortEntry 17 }

------------------------------------------------------------------
--								--
--				End of				--
--			    MRM Basic Group			--
--								--
------------------------------------------------------------------
------------------------------------------------------------------
--								--
--				Start of			--
--			   MRM Monitor Group			--
--								--
------------------------------------------------------------------

--
--	MRM Monitor Repeater Level Objects
--

mrmMonitorRepTable	OBJECT-TYPE
		SYNTAX			SEQUENCE OF MrmMonitorRepEntry
		ACCESS			not-accessible
		STATUS			mandatory
		DESCRIPTION
"Table of performance and error statistics for the ports."
		::= {mrmMonRepeaterPackage 1}

mrmMonitorRepEntry	OBJECT-TYPE
		SYNTAX			MrmMonitorRepEntry
		ACCESS			not-accessible
		STATUS			mandatory
		DESCRIPTION "
This table provides statistical and control information concerning the
entire repeater."
		INDEX			{ mrmMonRepServiceId }
		::= {mrmMonitorRepTable 1}

		MrmMonitorRepEntry ::= SEQUENCE {
			mrmMonRepServiceId			INTEGER,

			mrmMonRepReadableFrames			Counter,
			mrmMonRepUnicastFrames			Counter,
			mrmMonRepMulticastFrames		Counter,
			mrmMonRepBroadcastFrames		Counter,

			mrmMonRepReadableOctets			Counter,
			mrmMonRepUnicastOctets			Counter,
			mrmMonRepMulticastOctets		Counter,
			mrmMonRepBroadcastOctets		Counter,

			mrmMonRepFCSErrors			Counter,
			mrmMonRepAlignmentErrors		Counter,
			mrmMonRepFrameTooLongs			Counter,
			mrmMonRepShortEvents			Counter,
			mrmMonRepRunts				Counter,
			mrmMonRepTxCollisions			Counter,
			mrmMonRepLateEvents			Counter,
			mrmMonRepVeryLongEvents			Counter,
			mrmMonRepDataRateMismatches		Counter,
			mrmMonRepAutoPartitions			Counter,
			mrmMonRepTotalErrors 			Counter,

			mrmMonRepBound0				Counter,
			mrmMonRepBound1				Counter,
			mrmMonRepBound2				Counter,
			mrmMonRepBound3				Counter,
			mrmMonRepBound4				Counter,
			mrmMonRepBound5				Counter,

			mrmMonRepAction				INTEGER,

			mrmMonRepBandwidthUsed			Counter,
			mrmMonRepErrorsPer10000Packets		Counter
		}

mrmMonRepServiceId OBJECT-TYPE
	SYNTAX			INTEGER
	ACCESS			read-only
	STATUS			mandatory
	DESCRIPTION "
This parameter is used as the index in this table. A modular chassis
contains potentially many repeater services. Each repeater service contains
a number of cards (or groups). This parameter allows one of those repeaters
to be selected."
	::= {mrmMonitorRepEntry 1}

mrmMonRepReadableFrames OBJECT-TYPE
	SYNTAX			Counter
	ACCESS			read-only
	STATUS			mandatory
	DESCRIPTION "
This counter is incremented by one for each frame whose OctetCount
is greater than or equal to minFrameSize and less than or equal to
maxFrameSize and for which FCSError is not asserted that is received
by the repeater.

NOTE: This counter does not really exist. It is calculated by adding together
all the port counters within this repeater."
	::= {mrmMonitorRepEntry 2}

mrmMonRepUnicastFrames OBJECT-TYPE
	SYNTAX			Counter
	ACCESS			read-only
	STATUS			mandatory
	DESCRIPTION "
This counter is incremented by one for each readable frame seen by the
Repeater that is addressed to a unicast (non Card) address."
	::= {mrmMonitorRepEntry 3}

mrmMonRepMulticastFrames OBJECT-TYPE
	SYNTAX			Counter
	ACCESS			read-only
	STATUS			mandatory
	DESCRIPTION "
This counter is incremented by one for each readable frame seen by the
Repeater that is addressed to a multicast (non broadcast) address."
	::= {mrmMonitorRepEntry 4}

mrmMonRepBroadcastFrames OBJECT-TYPE
	SYNTAX			Counter
	ACCESS			read-only
	STATUS			mandatory
	DESCRIPTION "
This counter is incremented by one for each readable frame seen by the
Repeater that is addressed to the broadcast address ffffffffffff."
	::= {mrmMonitorRepEntry 5}

mrmMonRepReadableOctets	OBJECT-TYPE
	SYNTAX			Counter
	ACCESS			read-only
	STATUS			mandatory
	DESCRIPTION "
This counter is incremented by the octet count for each readable
frame received by the repeater.

NOTE: This counter does not really exist. It is calculated by adding together
all the port counters within this repeater."
	::= {mrmMonitorRepEntry 6}

mrmMonRepUnicastOctets	 OBJECT-TYPE
	SYNTAX			Counter
	ACCESS			read-only
	STATUS			mandatory
	DESCRIPTION "
This object is the number of octets contained in valid frames that
have been received on this port in which the destination field was a
unicast address.

The approximate minimum time for rollover of this counter is 58
minutes."
	::= {mrmMonitorRepEntry 7}

mrmMonRepMulticastOctets	 OBJECT-TYPE
	SYNTAX			Counter
	ACCESS			read-only
	STATUS			mandatory
	DESCRIPTION "
This object is the number of octets contained in valid frames that
have been received on this port in which the destination was a
multicast address.

The approximate minimum time for rollover of this counter is 58
minutes."
	::= {mrmMonitorRepEntry 8}

mrmMonRepBroadcastOctets	 OBJECT-TYPE
	SYNTAX			Counter
	ACCESS			read-only
	STATUS			mandatory
	DESCRIPTION "
This object is the number of octets contained in valid frames that
have been received on this port in which the destination was the
broadcast address ffffffffffff. By attaching a gauge to this counter
one can monitor the port for broadcast storms. Action can then be taken
to automatically recover network normal operation.

The approximate minimum time for rollover of this counter is 58
minutes."
	::= { mrmMonitorRepEntry 9 }

mrmMonRepFCSErrors OBJECT-TYPE
	SYNTAX			Counter
	ACCESS			read-only
	STATUS			mandatory
	DESCRIPTION "
This counter is incremented by one for each frame with an FCS error
that does not have a framing error and which is of legal frame size
received by the repeater.

NOTE: This counter does not really exist. It is calculated by adding together
all the port counters within this repeater."
	::= { mrmMonitorRepEntry 10 }

mrmMonRepAlignmentErrors OBJECT-TYPE
	SYNTAX			Counter
	ACCESS			read-only
	STATUS			mandatory
	DESCRIPTION "
This counter is incremented by one for each frame with an FCS error
that does have a framing error and which is of legal frame size
received by the repeater.

NOTE: This counter does not really exist. It is calculated by adding together
all the port counters within this repeater."
	::= { mrmMonitorRepEntry 11 }

mrmMonRepFrameTooLongs OBJECT-TYPE
	SYNTAX			Counter
	ACCESS			read-only
	STATUS			mandatory
	DESCRIPTION "
This counter is incremented by one for each frame whose octet count
is greater than the max frame size that is received by the repeater.

NOTE: This counter does not really exist. It is calculated by adding together
all the port counters within this repeater."
	::= { mrmMonitorRepEntry 12 }

mrmMonRepShortEvents OBJECT-TYPE
	SYNTAX			Counter
	ACCESS			read-only
	STATUS			mandatory
	DESCRIPTION "
This counter is incremented by one for each carrier event whose
duration is less than short event max time that is detected by the
repeater.

NOTE: This counter does not really exist. It is calculated by adding together
all the port counters within this repeater."
	::= { mrmMonitorRepEntry 13 }

mrmMonRepRunts	OBJECT-TYPE
	SYNTAX			Counter
	ACCESS			read-only
	STATUS			mandatory
	DESCRIPTION "
This counter is incremented by one for each carrier event whose
duration is greater than short event max time and less than valid
packet min time and which does not suffer a collision detected by
the repeater.

NOTE: This counter does not really exist. It is calculated by adding together
all the port counters within this repeater."
	::= { mrmMonitorRepEntry 14 }

mrmMonRepTxCollisions	 OBJECT-TYPE
	SYNTAX			Counter
	ACCESS			read-only
	STATUS			mandatory
	DESCRIPTION "
This counter is incremented by one for any CarrierEvent signal on any
port of this repeater for which the CollisionEvent signal on this port
is asserted.
The approximate minimum time for rollover of this counter is 16
hours."
	::= {mrmMonitorRepEntry 15}

mrmMonRepLateEvents OBJECT-TYPE
	SYNTAX			Counter
	ACCESS			read-only
	STATUS			mandatory
	DESCRIPTION "
This counter is incremented by one each time a collisions occurs
after valid packet min time, a late event is counted as both a
collision and as a late event.

NOTE: This counter does not really exist. It is calculated by adding together
all the port counters within this repeater."
	::= { mrmMonitorRepEntry 16 }

mrmMonRepVeryLongEvents OBJECT-TYPE
	SYNTAX			Counter
	ACCESS			read-only
	STATUS			mandatory
	DESCRIPTION "
This counter is incremented by one each time a carrier event
occurs whose duration is greater than the MAU Jabber Lockup
Protection time.

NOTE: This counter does not really exist. It is calculated by adding together
all the port counters within this repeater."
	::= { mrmMonitorRepEntry 17 }

mrmMonRepDataRateMismatches OBJECT-TYPE
	SYNTAX			Counter
	ACCESS			read-only
	STATUS			mandatory
	DESCRIPTION "
This counter is incremented by one each time a packet has been received
by this repeater with the data rate detectably mismatched from the local
frequency.

NOTE: This counter does not really exist. It is calculated by adding together
all the port counters within this repeater."
	::= { mrmMonitorRepEntry 18 }

mrmMonRepAutoPartitions OBJECT-TYPE
	SYNTAX			Counter
	ACCESS			read-only
	STATUS			mandatory
	DESCRIPTION "
This counter is incremented by one each time the repeater has automatically
partitioned any port.

NOTE: This counter does not really exist. It is calculated by adding together
all the port counters within this repeater."
	::= { mrmMonitorRepEntry 19 }

mrmMonRepTotalErrors OBJECT-TYPE
	SYNTAX	Counter
	ACCESS	read-only
	STATUS	mandatory
	DESCRIPTION "
The total number of errors which have occurred on all ports on all groups
of this repeater. This counter is the summation of the values of the
mrmMonCardTotalErrors counters for all of the cards in the repeater.

It is the sum of the following:
	FCS, Alignment, Frames Too Long, Short Events,
	Late Events, Very Long Events and Data Rate Mismatches.

As a general indicator the individual error counters are too detailed.
This parameter gives a very good monitor type parameter."
	::= { mrmMonitorRepEntry 20 }

mrmMonRepBound0		OBJECT-TYPE
	SYNTAX			Counter
	ACCESS			read-only
	STATUS			mandatory
	DESCRIPTION "
This object is a summation of the number of frames (including error frames)
with a length of 64 octets which were received by each port on every card of
this repeater."
	::= {mrmMonitorRepEntry 21}

mrmMonRepBound1			OBJECT-TYPE
	SYNTAX			Counter
	ACCESS			read-only
	STATUS			mandatory
	DESCRIPTION "
This object is a summation of the number of frames (including error frames)
with a length of between 65 and 127 octets inclusive which were received
by each port on every card of this repeater."
	::= {mrmMonitorRepEntry 22}

mrmMonRepBound2		OBJECT-TYPE
	SYNTAX			Counter
	ACCESS			read-only
	STATUS			mandatory
	DESCRIPTION "
This object is a summation of the number of frames (including error frames)
with a length of between 128 and 255 octets inclusive which were received
by each port on every card of this repeater."
	::= {mrmMonitorRepEntry 23}

mrmMonRepBound3		OBJECT-TYPE
	SYNTAX			Counter
	ACCESS			read-only
	STATUS			mandatory
	DESCRIPTION "
This object is a summation of the number of frames (including error frames)
with a length of between 256 and 511 octets inclusive which were received
by each port on every card of this repeater."
	::= {mrmMonitorRepEntry 24}

mrmMonRepBound4		OBJECT-TYPE
	SYNTAX			Counter
	ACCESS			read-only
	STATUS			mandatory
	DESCRIPTION "
This object is a summation of the number of frames (including error frames)
with a length of between 512 and 1023 octets inclusive which were received
by each port on every card of this repeater."
	::= {mrmMonitorRepEntry 25}

mrmMonRepBound5		OBJECT-TYPE
	SYNTAX			Counter
	ACCESS			read-only
	STATUS			mandatory
	DESCRIPTION "
This object is a summation of the number of frames (including error frames)
with a length of between 1024 and 1518 octets inclusive which were received
by each port on every card of this repeater."
	::= {mrmMonitorRepEntry 26}

mrmMonRepAction OBJECT-TYPE
	SYNTAX	INTEGER {
			clearCounters		(1),
			noAction		(128)
		}
	ACCESS			read-write
	STATUS			mandatory
	DESCRIPTION "
This object allows repeater stats specific actions to be implemented. There
is only one action currently defined, 'clearCounters'. Writing this
value to a repeater entry will clear ALL counters in this repeater.
That include port stats, card and repeater totals. If this object is read then
noAction will be returned."
	::= { mrmMonitorRepEntry 27 }

mrmMonRepBandwidthUsed         OBJECT-TYPE
        SYNTAX                  Counter
        ACCESS                  read-only
        STATUS                  mandatory
        DESCRIPTION "
	This is a high level 'smart MIB' object. This object provides a running
	average of the bandwidth in use. This value is calculated locally on the
	agent and so does not require processor bandwidth from the management
	station or occupy valuable network bandwidth communicating with that
	station.
	By default an agent supporting this parameter will exhibit the following
	characteristics:

	1)	The parameter will be recalculated at approx 15 second intervals
	2)	Every calculation period the device will read the value
		of rptrMonitorPortReadableOctets.
	3)	The calculation will be performed on the most recent 4 samples as
		follows:

		 4
		Sum(sample(i)/(time(i) * K)) * 100/4
		i=1

		Sample(i) is rptrMonitorPortReadableOctets(i)-rptrMonitorPortReadableOctets(i-1)
		time(i) is the time between sample(i-1) and sample(i)
		K is the max bytes per unit time (i.e. the available bandwidth K
		depends on the ring speed.

		The value is expressed as a percentage.

		A default threshold exists on this average so that if a calculated
		average exceeds 15% a trap will be sent to the management station.
		Further traps will not be sent until the average drops to below 10%.

		A particular device may provide a means of changing the number of samples,
		the averaging period, threshold and threshold action if it so wishes."
        ::= {mrmMonitorRepEntry 28}

mrmMonRepErrorsPer10000Packets OBJECT-TYPE
        SYNTAX                  Counter
        ACCESS                  read-only
        STATUS                  mandatory
        DESCRIPTION     "
	This is a high level 'smart MIB' object. This object provides a running
        average of the number of errors per 10000 packets. This is an error
	rate, and is calculated over the number of packets received in the
	sample periods, and not on every 10000 packets.
	This value is calculated locally on the agent and so does not require
	processor bandwidth from a management station or occupy valuable
	network bandwidth communicating with that station.

	By default an agent supporting this parameter will exhibit the following
	behaviour:

	1)	The parameter will be recalculated at approx 15 second intervals.
	2)	Every calculation period the device will read the value of
		rptrMonitorPortTotalErrors and rptrMonitorPortReadableFrames.
	3)	The calculation will be performed on the most recent 4 samples as
		follows:

			 4
		10000 *	Sum(Errors(i)/Frames(i))
			i=1

		Errors(i) = rptrMonitorPortTotalErrors(i)-rptrMonitorPortTotalErrors(i-1)
		Frames(i) = rptrMonitorPortReadableFrames(i)-rptrMonitorPortReadableFrames(i-1)

	The value is an integer number of errors per 10,000 packets received by this
	repeater.

	A default threshold exists on this average so that if a calculated average
	exceeds 200 (i.e. 2% of frames are in error) a trap will be sent to the
	management station.  Further traps will not be sent until the average drops
	to below 100 (i.e. 1% of frames are in error).

	A particular device may provide a means of changing the number of samples,
	the averaging period and threshold if it so wishes."
        ::= {mrmMonitorRepEntry 29}

--
--
--	MRM Monitor Card Table
--

mrmMonitorCardTable	OBJECT-TYPE
		SYNTAX			SEQUENCE OF MrmMonitorCardEntry
		ACCESS			not-accessible
		STATUS			mandatory
		DESCRIPTION "
This table contains parameters about the various repeater cards within
the chassis. The table is indexed using the 'serviceIndex' for the repeater
and the slot number within that repeater."
		::= {mrmMonCardPackage 1}

mrmMonitorCardEntry	OBJECT-TYPE
		SYNTAX		MrmMonitorCardEntry
		ACCESS		not-accessible
		STATUS		mandatory
		DESCRIPTION
"Status information and control variables for the ports on a single card."
		INDEX		{ 	mrmMonCardServiceId,
					mrmMonCardIndex
				}
		::= {mrmMonitorCardTable 1}

		MrmMonitorCardEntry ::= SEQUENCE {
			mrmMonCardServiceId			INTEGER,
			mrmMonCardIndex				INTEGER,

			mrmMonCardReadableFrames		Counter,
			mrmMonCardUnicastFrames			Counter,
			mrmMonCardMulticastFrames		Counter,
			mrmMonCardBroadcastFrames		Counter,

			mrmMonCardReadableOctets		Counter,
			mrmMonCardUnicastOctets			Counter,
			mrmMonCardMulticastOctets		Counter,
			mrmMonCardBroadcastOctets		Counter,

			mrmMonCardFCSErrors			Counter,
			mrmMonCardAlignmentErrors		Counter,
			mrmMonCardFrameTooLongs			Counter,
			mrmMonCardShortEvents			Counter,
			mrmMonCardRunts				Counter,
			mrmMonCardLateEvents			Counter,
			mrmMonCardVeryLongEvents		Counter,
			mrmMonCardDataRateMismatches		Counter,
			mrmMonCardAutoPartitions		Counter,
			mrmMonCardTotalErrors			Counter,

			mrmMonCardBound0			Counter,
			mrmMonCardBound1			Counter,
			mrmMonCardBound2			Counter,
			mrmMonCardBound3			Counter,
			mrmMonCardBound4			Counter,
			mrmMonCardBound5			Counter,

			mrmMonCardClearCounters			INTEGER,

			mrmMonCardBandwidthUsed			Counter,
			mrmMonCardErrorsPer10000Packets		Counter
		}

mrmMonCardServiceId OBJECT-TYPE
	SYNTAX			INTEGER
	ACCESS			read-only
	STATUS			mandatory
	DESCRIPTION "
This parameter is used as the first of two indices in this table. A
modular chassis contains potentially many repeater services. Each
repeater service contains a number of cards (or groups). In order to
uniquely identify a port it is necessary to specify both the repeater
service and the card within that repeater."
	::= {mrmMonitorCardEntry 1}

mrmMonCardIndex		OBJECT-TYPE
	SYNTAX			INTEGER
	ACCESS			read-only
	STATUS			mandatory
	DESCRIPTION "
This is the second part of the key on this table. Having selected one
of the repeaters within the chassis it is necessary to identify the
card within that repeater."
	::= {mrmMonitorCardEntry 2}

mrmMonCardReadableFrames OBJECT-TYPE
	SYNTAX			Counter
	ACCESS			read-only
	STATUS			mandatory
	DESCRIPTION "
This counter is incremented by one for each frame whose OctetCount
is greater than or equal to minFrameSize and less than or equal to
maxFrameSize and for which FCSError is not asserted that is received for
any port on this card."
	::= {mrmMonitorCardEntry 3}

mrmMonCardUnicastFrames OBJECT-TYPE
	SYNTAX			Counter
	ACCESS			read-only
	STATUS			mandatory
	DESCRIPTION "
This counter is incremented by one for each readable frame seen by the
Card that is addressed to a unicast (non Card) address."
	::= {mrmMonitorCardEntry 4}

mrmMonCardMulticastFrames OBJECT-TYPE
	SYNTAX			Counter
	ACCESS			read-only
	STATUS			mandatory
	DESCRIPTION "
This counter is incremented by one for each readable frame seen by the
Card that is addressed to a multicast (non broadcast) address."
	::= {mrmMonitorCardEntry 5}

mrmMonCardBroadcastFrames OBJECT-TYPE
	SYNTAX			Counter
	ACCESS			read-only
	STATUS			mandatory
	DESCRIPTION "
This counter is incremented by one for each readable frame seen by the
Card that is addressed to the broadcast address ffffffffffff."
	::= {mrmMonitorCardEntry 6}

mrmMonCardReadableOctets OBJECT-TYPE
	SYNTAX			Counter
	ACCESS			read-only
	STATUS			mandatory
	DESCRIPTION "
This counter is incremented by the octet count for each readable
frame received by any port on this card."
	::= {mrmMonitorCardEntry 7}

mrmMonCardUnicastOctets	 OBJECT-TYPE
	SYNTAX			Counter
	ACCESS			read-only
	STATUS			mandatory
	DESCRIPTION "
This object is the number of octets contained in valid frames that
have been received on this port in which the destination field was a
unicast address.

The approximate minimum time for rollover of this counter is 58
minutes."
	::= {mrmMonitorCardEntry 8}

mrmMonCardMulticastOctets	 OBJECT-TYPE
	SYNTAX			Counter
	ACCESS			read-only
	STATUS			mandatory
	DESCRIPTION "
This object is the number of octets contained in valid frames that
have been received on this port in which the destination was a
multicast address.

The approximate minimum time for rollover of this counter is 58
minutes."
	::= {mrmMonitorCardEntry 9}

mrmMonCardBroadcastOctets	 OBJECT-TYPE
	SYNTAX			Counter
	ACCESS			read-only
	STATUS			mandatory
	DESCRIPTION "
This object is the number of octets contained in valid frames that
have been received on this port in which the destination was the
broadcast address ffffffffffff. By attaching a gauge to this counter
one can monitor the port for broadcast storms. Action can then be taken
to automatically recover network normal operation.

The approximate minimum time for rollover of this counter is 58
minutes."
	::= { mrmMonitorCardEntry 10 }

mrmMonCardFCSErrors OBJECT-TYPE
	SYNTAX			Counter
	ACCESS			read-only
	STATUS			mandatory
	DESCRIPTION "
This counter is incremented by one for each frame with an FCS error
that does not have a framing error and which is of legal frame size."
	::= {mrmMonitorCardEntry 11}

mrmMonCardAlignmentErrors OBJECT-TYPE
	SYNTAX			Counter
	ACCESS			read-only
	STATUS			mandatory
	DESCRIPTION "
This counter is incremented by one for each frame with an FCS error
that does have a framing error and which is of legal frame size ."
	::= {mrmMonitorCardEntry 12}

mrmMonCardFrameTooLongs OBJECT-TYPE
	SYNTAX			Counter
	ACCESS			read-only
	STATUS			mandatory
	DESCRIPTION "
This counter is incremented by one for each frame whose octet count
is greater than the max frame size that is received by the repeater."
	::= {mrmMonitorCardEntry 13}

mrmMonCardShortEvents	OBJECT-TYPE
	SYNTAX			Counter
	ACCESS			read-only
	STATUS			mandatory
	DESCRIPTION "
This counter is incremented by one for each carrier event whose
duration is less than short event max time that is detected."
	::= {mrmMonitorCardEntry 14}

mrmMonCardRunts		OBJECT-TYPE
	SYNTAX			Counter
	ACCESS			read-only
	STATUS			mandatory
	DESCRIPTION "
This counter is incremented by one for each carrier event whose
duration is greater than short event max time and less than valid
packet min time and which does not suffer a collision."
	::= {mrmMonitorCardEntry 15}

mrmMonCardLateEvents OBJECT-TYPE
	SYNTAX			Counter
	ACCESS			read-only
	STATUS			mandatory
	DESCRIPTION "
This counter is incremented by one each time a collisions occurs
after valid packet min time, a late event is counted as both a
collision and as a late event."
	::= {mrmMonitorCardEntry 16}

mrmMonCardVeryLongEvents OBJECT-TYPE
	SYNTAX			Counter
	ACCESS			read-only
	STATUS			mandatory
	DESCRIPTION "
This counter is incremented by one each time a carrier event
occurs whose duration is greater than the MAU Jabber Lockup
Protection time."
	::= {mrmMonitorCardEntry 17}

mrmMonCardDataRateMismatches OBJECT-TYPE
	SYNTAX			Counter
	ACCESS			read-only
	STATUS			mandatory
	DESCRIPTION "
This counter is incremented by one each time a packet has been received
with the data rate detectably mismatched from the local frequency."
	::= {mrmMonitorCardEntry 18}

mrmMonCardAutoPartitions OBJECT-TYPE
	SYNTAX			Counter
	ACCESS			read-only
	STATUS			mandatory
	DESCRIPTION "
This counter is incremented by one each time the repeater has automatically
partitioned any port."
	::= {mrmMonitorCardEntry 19}

mrmMonCardTotalErrors OBJECT-TYPE
	SYNTAX			Counter
	ACCESS			read-only
	STATUS			mandatory
	DESCRIPTION "
The total number of errors which have occurred on all ports of this
card. This counter is the summation of the values of other error counters
(for each port), namely:

	FCS Errors,
	Alignment Errors,
	Frames Too Long,
	Short Events,
	Late Events,
	Very Long Events,
	Data Rate Mismatches.

This counter is redundant in the sense that it is the summation of
information already available through other objects.  However, it is
included specifically because the regular retrieval of this object as
a means of tracking the health of a port provides a considerable
optimization of network management traffic over the otherwise
necessary retrieval of the summed counters."

	::= {mrmMonitorCardEntry 20}

mrmMonCardBound0		OBJECT-TYPE
	SYNTAX			Counter
	ACCESS			read-only
	STATUS			mandatory
	DESCRIPTION "
This object is a summation of the number of frames (including error frames)
with a length of 64 octets which were received by each port on this card."
	::= {mrmMonitorCardEntry 21}

mrmMonCardBound1		OBJECT-TYPE
	SYNTAX			Counter
	ACCESS			read-only
	STATUS			mandatory
	DESCRIPTION "
This object is a summation of the number of frames (including error frames)
with a length of between 65 and 127 octets inclusive which were received
by each port on this card."
	::= {mrmMonitorCardEntry 22}

mrmMonCardBound2		OBJECT-TYPE
	SYNTAX			Counter
	ACCESS			read-only
	STATUS			mandatory
	DESCRIPTION "
This object is a summation of the number of frames (including error frames)
with a length of between 128 and 255 octets inclusive which were received
by each port on this card."
	::= {mrmMonitorCardEntry 23}

mrmMonCardBound3		OBJECT-TYPE
	SYNTAX			Counter
	ACCESS			read-only
	STATUS			mandatory
	DESCRIPTION "
This object is a summation of the number of frames (including error frames)
with a length of between 256 and 511 octets inclusive which were received
by each port on this card."
	::= {mrmMonitorCardEntry 24}

mrmMonCardBound4		OBJECT-TYPE
	SYNTAX			Counter
	ACCESS			read-only
	STATUS			mandatory
	DESCRIPTION "
This object is a summation of the number of frames (including error frames)
with a length of between 512 and 1023 octets inclusive which were received
by each port on this card."
	::= {mrmMonitorCardEntry 25}

mrmMonCardBound5		OBJECT-TYPE
	SYNTAX			Counter
	ACCESS			read-only
	STATUS			mandatory
	DESCRIPTION "
This object is a summation of the number of frames (including error frames)
with a length of between 1024 and 1518 octets inclusive which were received
by each port on this card."
	::= {mrmMonitorCardEntry 26}

mrmMonCardClearCounters OBJECT-TYPE
	SYNTAX		INTEGER {
			noChangeCounters	(1),
			clearCounters		(2)
		}
	ACCESS			read-write
	STATUS			mandatory
	DESCRIPTION "
This attribute allows all counters on this Card to be cleared. If this
object is read then it will return noChangeCounters(1)."
	::= {mrmMonitorCardEntry 27}

mrmMonCardBandwidthUsed         OBJECT-TYPE
        SYNTAX                  Counter
        ACCESS                  read-only
        STATUS                  mandatory
        DESCRIPTION "
	This is a high level 'smart MIB' object. This object provides a running
	average of the bandwidth in use. This value is calculated locally on the
	agent and so does not require processor bandwidth from the management
	station or occupy valuable network bandwidth communicating with that
	station.
	By default an agent supporting this parameter will exhibit the following
	characteristics:

	1)	The parameter will be recalculated at approx 15 second intervals
	2)	Every calculation period the device will read the value
		of rptrMonitorGroupTotalOctets.
	3)	The calculation will be performed on the most recent 4 samples as
		follows:

		 4
		Sum(sample(i)/(time(i) * K)) * 100/4
		i=1

		Sample(i) is rptrMonitorGroupTotalOctets(i)-rptrMonitorGroupTotalOctets(i-1)
		time(i) is the time between sample(i-1) and sample(i)
		K is the max bytes per unit time (i.e. the available bandwidth K
		depends on the ring speed.

	The value is expressed as a percentage.

	A default threshold exists on this average so that if a calculated
	average exceeds 15% a trap will be sent to the management station.
	Further traps will not be sent until the average drops to below 10%.

	A particular device may provide a means of changing the number of samples,
	the averaging period, threshold and threshold action if it so wishes."
        ::= {mrmMonitorCardEntry 28}

mrmMonCardErrorsPer10000Packets OBJECT-TYPE
        SYNTAX                  Counter
        ACCESS                  read-only
        STATUS                  mandatory
        DESCRIPTION     "
	This is a high level 'smart MIB' object. This object provides a running
        average of the number of errors per 10000 packets. This is an error
	rate, and is calculated over the number of packets received in the
	sample periods, and not on every 10000 packets.
	This value is calculated locally on the agent and so does not require
	processor bandwidth from a management station or occupy valuable
	network bandwidth communicating with that station.

	By default an agent supporting this parameter will exhibit the following
	behaviour:

	1)	The parameter will be recalculated at approx 15 second intervals.
	2)	Every calculation period the device will read the value of
		rptrMonitorGroupTotalErrors and rptrMonitorGroupTotalFrames.
	3)	The calculation will be performed on the most recent 4 samples as
		follows:

			 4
		10000 *	Sum(Errors(i)/Frames(i))
			i=1

		Errors(i) = rptrMonitorGroupTotalErrors(i)-rptrMonitorGroupTotalErrors(i-1)
		Frames(i) = rptrMonitorGroupTotalFrames(i)-rptrMonitorGroupTotalFrames(i-1)

	The value is an integer number of errors per 10,000 packets received by this
	repeater.

	A default threshold exists on this average so that if a calculated average
	exceeds 200 (i.e. 2% of frames are in error) a trap will be sent to the
	management station.  Further traps will not be sent until the average drops
	to below 100 (i.e. 1% of frames are in error).

	A particular device may provide a means of changing the number of samples,
	the averaging period and threshold if it so wishes."
        ::= {mrmMonitorCardEntry 29}

--
--	MRM Monitor Port Table
--

mrmMonitorPortTable	OBJECT-TYPE
	SYNTAX			SEQUENCE OF MrmMonitorPortEntry
	ACCESS			not-accessible
	STATUS			mandatory
	DESCRIPTION
"Table of performance and error statistics for the ports."
	::= {mrmMonPortPackage 1}

mrmMonitorPortEntry	OBJECT-TYPE
	SYNTAX			MrmMonitorPortEntry
	ACCESS			not-accessible
	STATUS			mandatory
	DESCRIPTION "
Performance and error statistics for a single port."
	INDEX			{mrmMonPortServiceId,
				 mrmMonPortCardIndex,
				 mrmMonPortIndex}
	::= {mrmMonitorPortTable 1}

	MrmMonitorPortEntry ::= SEQUENCE {
			mrmMonPortServiceId		INTEGER,
			mrmMonPortCardIndex		INTEGER,
			mrmMonPortIndex			INTEGER,

			mrmMonPortReadableFrames	Counter,
			mrmMonPortUnicastFrames		Counter,
			mrmMonPortMulticastFrames	Counter,
			mrmMonPortBroadcastFrames	Counter,

			mrmMonPortReadableOctets	Counter,
			mrmMonPortUnicastOctets		Counter,
			mrmMonPortMulticastOctets	Counter,
			mrmMonPortBroadcastOctets	Counter,

			mrmMonPortFCSErrors		Counter,
			mrmMonPortAlignmentErrors	Counter,
			mrmMonPortFrameTooLongs		Counter,
			mrmMonPortShortEvents		Counter,
			mrmMonPortRunts			Counter,
			mrmMonPortCollisions		Counter,
			mrmMonPortLateEvents		Counter,
			mrmMonPortVeryLongEvents	Counter,
			mrmMonPortDataRateMismatches	Counter,
			mrmMonPortAutoPartitions	Counter,
			mrmMonPortTotalErrors		Counter,

			mrmMonPortBound0		Counter,
			mrmMonPortBound1		Counter,
			mrmMonPortBound2		Counter,
			mrmMonPortBound3		Counter,
			mrmMonPortBound4		Counter,
			mrmMonPortBound5		Counter,

			mrmMonPortBandwidthUsed		Counter,
			mrmMonPortErrorsPer10000Packets	Counter,

			mrmMonPortClearCounters		INTEGER,

			mrmMonPortLastAddress		OCTET STRING,
			mrmMonPortAddressChanges	Counter
		}

mrmMonPortServiceId	OBJECT-TYPE
	SYNTAX			INTEGER (1..1024)
	ACCESS			read-only
	STATUS			mandatory
	DESCRIPTION "
This parameter selects one of the repeaters within the chassis. This
forms the first, most significant index column. Having selected a
repeater one must select a card then port within that repeater."
	::= {mrmMonitorPortEntry 1}

mrmMonPortCardIndex	OBJECT-TYPE
	SYNTAX			INTEGER
	ACCESS			read-only
	STATUS			mandatory
	DESCRIPTION "
This attribute uniquely identifies this Card within the repeater, it is
part of the index for the port table."
	::= {mrmMonitorPortEntry 2}

mrmMonPortIndex		OBJECT-TYPE
	SYNTAX			INTEGER
	ACCESS			read-only
	STATUS			mandatory
	DESCRIPTION "
This attribute uniquely identifies this port within the Card, it is
part of the index for the port table."
	::= {mrmMonitorPortEntry 3}

mrmMonPortReadableFrames OBJECT-TYPE
	SYNTAX			Counter
	ACCESS			read-only
	STATUS			mandatory
	DESCRIPTION "
This object is the number of frames of valid frame length that have
been received on this port.  This counter is incremented by one for
each frame received on this port whose OctetCount is greater than or
equal to minFrameSize and less than or equal to maxFrameSize (Ref:
IEEE 802.3 Std, 4.4.2.1) and for which the FCSError and CollisionEvent
signals are not asserted.

This statistic provides one of the parameters necessary for obtaining
the packet error rate.  The approximate minimum time for rollover of
this counter is 80 hours."
	::= {mrmMonitorPortEntry 4}

mrmMonPortUnicastFrames OBJECT-TYPE
	SYNTAX			Counter
	ACCESS			read-only
	STATUS			mandatory
	DESCRIPTION "
This counter is incremented by one for each readable frame seen by the
Card that is addressed to a unicast (non Card) address."
	::= {mrmMonitorPortEntry 5}

mrmMonPortMulticastFrames OBJECT-TYPE
	SYNTAX			Counter
	ACCESS			read-only
	STATUS			mandatory
	DESCRIPTION "
This counter is incremented by one for each readable frame seen by the
Card that is addressed to a multicast (non broadcast) address."
	::= {mrmMonitorPortEntry 6}

mrmMonPortBroadcastFrames OBJECT-TYPE
	SYNTAX			Counter
	ACCESS			read-only
	STATUS			mandatory
	DESCRIPTION "
This counter is incremented by one for each readable frame seen by the
Card that is addressed to the broadcast address."
	::= {mrmMonitorPortEntry 7}

mrmMonPortReadableOctets OBJECT-TYPE
	SYNTAX			Counter
	ACCESS			read-only
	STATUS			mandatory
	DESCRIPTION "
This object is the number of octets contained in valid frames that
have been received on this port.  This counter is incremented by
OctetCount for each frame received on this port which has been
determined to be a readable frame.

This statistic provides an indicator of the total data transferred.
The approximate minimum time for rollover of this counter is 58
minutes."
	::= {mrmMonitorPortEntry 8}

mrmMonPortUnicastOctets	 OBJECT-TYPE
	SYNTAX			Counter
	ACCESS			read-only
	STATUS			mandatory
	DESCRIPTION "
This object is the number of octets contained in valid frames that
have been received on this port in which the destination field was a
unicast address.

The approximate minimum time for rollover of this counter is 58
minutes."
	::= {mrmMonitorPortEntry 9}

mrmMonPortMulticastOctets	 OBJECT-TYPE
	SYNTAX			Counter
	ACCESS			read-only
	STATUS			mandatory
	DESCRIPTION "
This object is the number of octets contained in valid frames that
have been received on this port in which the destination was a
multicast address.

The approximate minimum time for rollover of this counter is 58
minutes."
	::= {mrmMonitorPortEntry 10}

mrmMonPortBroadcastOctets	 OBJECT-TYPE
	SYNTAX			Counter
	ACCESS			read-only
	STATUS			mandatory
	DESCRIPTION "
This object is the number of octets contained in valid frames that
have been received on this port in which the destination was the
broadcast address ffffffffffff. By attaching a gauge to this counter
one can monitor the port for broadcast storms. Action can then be taken
to automatically recover network normal operation.

The approximate minimum time for rollover of this counter is 58
minutes."
	::= { mrmMonitorPortEntry 11 }

mrmMonPortFCSErrors	 OBJECT-TYPE
	SYNTAX			Counter
	ACCESS			read-only
	STATUS			mandatory
	DESCRIPTION "
This counter is incremented by one for each frame received on this
port with the FCSError signal asserted and the FramingError and
CollisionEvent signals deasserted and whose OctetCount is greater than
or equal to minFrameSize and less than or equal to maxFrameSize (Ref:
4.4.2.1, IEEE 802.3 Std).

The approximate minimum time for rollover of this counter is 80
hours."
	::= { mrmMonitorPortEntry 12 }

mrmMonPortAlignmentErrors OBJECT-TYPE
	SYNTAX			Counter
	ACCESS			read-only
	STATUS			mandatory
	DESCRIPTION "
This counter is incremented by one for each frame received on this
port with the FCSError and FramingError signals asserted and
CollisionEvent signal deasserted and whose OctetCount is greater than
or equal to minFrameSize and less than or equal to maxFrameSize (Ref:
IEEE 802.3 Std, 4.4.2.1).  If rptrMonitorPortAlignmentErrors is
incremented then the rptrMonitorPortFCSErrors Counter shall not be
incremented for the same frame.

The approximate minimum time for rollover of this
counter is 80 hours."
	::= {mrmMonitorPortEntry 13}

mrmMonPortFrameTooLongs	 OBJECT-TYPE
	SYNTAX			Counter
	ACCESS			read-only
	STATUS			mandatory
	DESCRIPTION "
This counter is incremented by one for each frame received on this
port whose OctetCount is greater than maxFrameSize (Ref: 4.4.2.1, IEEE
802.3 Std).  If this parameter is incremented then neither the
alignment error nor the FCS error counters shall be incremented for
the frame.

The approximate minimum time for rollover of this counter is 61 days."
	::= {mrmMonitorPortEntry 14}

mrmMonPortShortEvents	 OBJECT-TYPE
	SYNTAX			Counter
	ACCESS			read-only
	STATUS			mandatory
	DESCRIPTION "
This counter is incremented by one for each CarrierEvent on this port
with ActivityDuration less than ShortEventMaxTime.  ShortEventMaxTime
is greater than 74 bit times and less than 82 bit times.
ShortEventMaxTime has tolerances included to provide for circuit
losses between a conformance test point at the AUI and the measurement
point within the state machine.

Note: shortEvents may indicate externally generated noise hits which
will cause the repeater to transmit Runts to its other ports, or
propagate a collision (which may be late) back to the transmitting DTE
and damaged frames to the rest of the network.

The approximate minimum time for rollover of this counter is 16
hours."
	::= {mrmMonitorPortEntry 15}

mrmMonPortRunts		 OBJECT-TYPE
	SYNTAX			Counter
	ACCESS			read-only
	STATUS			mandatory
	DESCRIPTION "
This counter is incremented by one for each CarrierEvent on this port
that meets one of the following two conditions.  Only one test need be
made.  a) The ActivityDuration is greater than ShortEventMaxTime and
less than ValidPacketMinTime and the CollisionEvent signal is
deasserted.  b) The OctetCount is less than 64, the ActivityDuration
is greater than ShortEventMaxTime and the CollisionEvent signal is
deasserted.  ValidPacketMinTime is greater than or equal to 552 bit
times and less than 565 bit times.

An event whose length is greater than 74 bit times but less than 82
bit times shall increment either the shortEvents counter or the runts
counter but not both.  A CarrierEvent greater than or equal to 552 bit
times but less than 565 bit times may or may not be counted as a runt.

ValidPacketMinTime has tolerances included to provide for circuit
losses between a conformance test point at the AUI and the measurement
point within the state machine.

Runts usually indicate collision fragments, a normal network event.
In certain situations associated with large diameter networks a
percentage of runts may exceed ValidPacketMinTime.

The approximate minimum time for rollover of this counter is 16
hours."
	::= {mrmMonitorPortEntry 16}

mrmMonPortCollisions	 OBJECT-TYPE
	SYNTAX			Counter
	ACCESS			read-only
	STATUS			mandatory
	DESCRIPTION "
This counter is incremented by one each time a collision is detected on
this port or when the CollisionEvent signal is asserted on this port.

The approximate minimum time for rollover of this counter is 16
hours."
	::= {mrmMonitorPortEntry 17}

mrmMonPortLateEvents	 OBJECT-TYPE
	SYNTAX			Counter
	ACCESS			read-only
	STATUS			mandatory
	DESCRIPTION "
This counter is incremented by one for each CarrierEvent on this port
in which the CollIn(X) variable transitions to the value SQE (Ref:
9.6.6.2, IEEE 802.3 Std) while the ActivityDuration is greater than
the LateEventThreshold.  Such a CarrierEvent is counted twice, as both
a collision and as a lateEvent.

The LateEventThreshold is greater than 480 bit times and less than 565
bit times.  LateEventThreshold has tolerances included to permit an
implementation to build a single threshold to serve as both the
LateEventThreshold and ValidPacketMinTime threshold.

The approximate minimum time for rollover of this counter is 81
hours."

	::= {mrmMonitorPortEntry 18}

mrmMonPortVeryLongEvents OBJECT-TYPE
	SYNTAX			Counter
	ACCESS			read-only
	STATUS			mandatory
	DESCRIPTION "
This counter is incremented by one for each CarrierEvent on this port
whose ActivityDuration is greater than the MAU Jabber Lockup
Protection timer TW3 (Ref: 9.6.1 & 9.6.5, IEEE 802.3 Std).  Other
counters may be incremented as appropriate."
	::= {mrmMonitorPortEntry 19}

mrmMonPortDataRateMismatches OBJECT-TYPE
	SYNTAX			Counter
	ACCESS			read-only
	STATUS			mandatory
	DESCRIPTION "
This counter is incremented by one for each frame received on this
port that meets all of the following conditions: a) The CollisionEvent
signal is not asserted.  b) The ActivityDuration is greater than
ValidPacketMinTime.  c) The frequency (data rate) is detectably
mismatched from the local transmit frequency.  The exact degree of
mismatch is vendor specific and is to be defined by the vendor for
conformance testing.

When this event occurs, other counters whose increment conditions were
satisfied may or may not also be incremented, at the implementor's
discretion.  Whether or not the repeater was able to maintain data
integrity is beyond the scope of this standard."
	::= {mrmMonitorPortEntry 20}

mrmMonPortAutoPartitions OBJECT-TYPE
	SYNTAX			Counter
	ACCESS			read-only
	STATUS			mandatory
	DESCRIPTION "
This counter is incremented by one for each time the repeater has
automatically partitioned this port.  The conditions that cause port
partitioning are specified in the partition state machine in Section 9
[IEEE 802.3 Std].  They are not differentiated here."
	::= {mrmMonitorPortEntry 21}

mrmMonPortTotalErrors	 OBJECT-TYPE
	SYNTAX			Counter
	ACCESS			read-only
	STATUS			mandatory
	DESCRIPTION "
The total number of errors which have occurred on this port.  This
counter is the summation of the values of other error counters (for
the same port), namely:

	FCS Errors,
	Alignment Errors,
	Frames Too Long,
	Short Events,
	Late Events,
	Very Long Events,
	Data Rate Mismatches.

This counter is redundant in the sense that it is the summation of
information already available through other objects.  However, it is
included specifically because the regular retrieval of this object as
a means of tracking the health of a port provides a considerable
optimization of network management traffic over the otherwise
necessary retrieval of the summed counters."

	::= {mrmMonitorPortEntry 22}

mrmMonPortBound0		OBJECT-TYPE
	SYNTAX			Counter
	ACCESS			read-only
	STATUS			mandatory
	DESCRIPTION "
This object is the number of frames (including error frames) with a length
of 64 octets which were received on this port."
	::= {mrmMonitorPortEntry 23}

mrmMonPortBound1		OBJECT-TYPE
	SYNTAX			Counter
	ACCESS			read-only
	STATUS			mandatory
	DESCRIPTION "
This object is the number of frames (including error frames) with a length
of between 65 and 127 octets inclusive which were received on this port."
	::= {mrmMonitorPortEntry 24}

mrmMonPortBound2		OBJECT-TYPE
	SYNTAX			Counter
	ACCESS			read-only
	STATUS			mandatory
	DESCRIPTION "
This object is the number of frames (including error frames) with a length
of between 128 and 255 octets inclusive which were received on this port."
	::= {mrmMonitorPortEntry 25}

mrmMonPortBound3		OBJECT-TYPE
	SYNTAX			Counter
	ACCESS			read-only
	STATUS			mandatory
	DESCRIPTION "
This object is the number of frames (including error frames) with a length
of between 256 and 511 octets inclusive which were received on this port."
	::= {mrmMonitorPortEntry 26}

mrmMonPortBound4		OBJECT-TYPE
	SYNTAX			Counter
	ACCESS			read-only
	STATUS			mandatory
	DESCRIPTION "
This object is the number of frames (including error frames) with a length
of between 512 and 1023 octets inclusive which were received on this port."
	::= {mrmMonitorPortEntry 27}

mrmMonPortBound5		OBJECT-TYPE
	SYNTAX			Counter
	ACCESS			read-only
	STATUS			mandatory
	DESCRIPTION "
This object is the number of frames (including error frames) with a length
of between 1024 and 1518 octets inclusive which were received on this port."
	::= {mrmMonitorPortEntry 28}

mrmMonPortBandwidthUsed 	OBJECT-TYPE
	SYNTAX			Counter
	ACCESS			read-only
	STATUS			mandatory
	DESCRIPTION "
This is a high level 'smart MIB' object. This object provides a running
average of the bandwidth in use. This value is calculated locally on the
agent and so does not require processor bandwidth from the management
station or occupy valuable network bandwidth communicating with that
station.
By default an agent supporting this parameter will exhibit the following
characteristics:

1)	The parameter will be recalculated at approx 15 second intervals
2)	Every calculation period the device will read the value
	of mrmMonPortReadableOctets.
3)	The calculation will be performed on the most recent 4 samples as
	follows:

	 4
	Sum(sample(i)/(time(i) * K)) * 100/4
	i=1

	Sample(i) is mrmMonPortReadableOctets(i)-mrmMonPortReadableOctets(i-1)
	time(i) is the time between sample(i-1) and sample(i)
	K is the max bytes per unit time (i.e. the available bandwidth K
		depends on the ring speed.

The value is expressed as a percentage.

A default threshold exists on this average so that if a calculated
average exceeds 15% a trap will be sent to the management station.
Further traps will not be sent until the average drops to below 10%.

A particular device may provide a means of changing the number of samples,
the averaging period, threshold and threshold action if it so wishes."
	::= {mrmMonitorPortEntry 29}

mrmMonPortErrorsPer10000Packets OBJECT-TYPE
	SYNTAX			Counter
	ACCESS			read-only
	STATUS			mandatory
	DESCRIPTION	"
This is a high level 'smart MIB' object. This object provides a running
average of the number of errors per 10000 packets. This is an error rate,
and is calculated over the number of packets received in the sample periods,
and not on every 10000 packets.  This value is calculated locally on the
agent and so does not require processor bandwidth from a management station
or occupy valuable network bandwidth communicating with that station.

By default an agent supporting this parameter will exhibit the following
behaviour:

1)	The parameter will be recalculated at approx 15 second intervals.
2)	Every calculation period the device will read the value of
	mrmMonPortTotalErrors and mrmMonPortReadableFrames.
3)	The calculation will be performed on the most recent 4 samples as
	follows:

	 4
	Sum(Errors(i)/Frames(i)) * 10000/4
	i=1

	Errors(i) = mrmMonPortTotalErrors(i)-mrmMonPortTotalErrors(i-1)
	Frames(i) = mrmMonPortReadableFrames(i)-mrmMonPortReadableFrames(i-1)

The value is an integer number of errors per 10,000 packets received by this
repeater.

A default threshold exists on this average so that if a calculated average
exceeds 200 (i.e. 2% of frames are in error) a trap will be sent to the
management station.  Further traps will not be sent until the average drops
to below 100 (i.e. 1% of frames are in error).

A particular device may provide a means of changing the number of samples,
the averaging period and threshold if it so wishes."
	::= {mrmMonitorPortEntry 30}

mrmMonPortClearCounters OBJECT-TYPE
	SYNTAX		INTEGER {
			noChangeCounters	(1),
			clearCounters		(2)
			}
	ACCESS			read-write
	STATUS			mandatory
	DESCRIPTION "
This attribute allows all counters on this Port to be cleared.  If read
this object will return noChangeCounters(1)."
	::= {mrmMonitorPortEntry 31}

mrmMonPortLastAddress OBJECT-TYPE
	SYNTAX	OCTET STRING
	ACCESS	read-only
	STATUS	mandatory
	DESCRIPTION "
This is the last MAC address seen on this port."
	::= {mrmMonitorPortEntry 32}

mrmMonPortAddressChanges OBJECT-TYPE
	SYNTAX	Counter
	ACCESS	read-only
	STATUS	mandatory
	DESCRIPTION "
This is a count of the number of times the MAC address on this port has
changed. A high number of changes indicates this is either an
inter-repeater link or a multi-drop segment."
	::= {mrmMonitorPortEntry 33}

--
--	MRM Dummy Monitor objects
--	These have been deprecated.
--	Please now use:	mrmMonRepeaterSmartPackage
--			mrmMonCardSmartPackage
--			mrmMonPortSmartPackage
--

trafficLevel		OBJECT-TYPE
	SYNTAX			Counter
	ACCESS			read-only
	STATUS			deprecated
	DESCRIPTION "
This is a dummy 'smart MIB' object which is used internally by the agent to
provide a running average of the bandwidth in use. It should not be accessed by
a management station and is used by the logic which calculates the value of
its associated object 'mrmMonPortBandwidthUsed'.

See 'mrmMonPortBandwidthUsed' for a description of how the bandwidth used
is calculated."
	::= {mrmMonDummyPackage 1}

errorFrames		OBJECT-TYPE
	SYNTAX			Counter
	ACCESS			read-only
	STATUS			deprecated
	DESCRIPTION	"
This is a dummy 'smart MIB' object which is used internally by the agent to
provide a running average of the error rate. It should not be accessed by a
management station and is used by the logic which calculates the value of
its associated object 'mrmMonPortErrorsPer10000Packets'.

See 'mrmMonPortErrorsPer10000Packets' for a description of how the error rate
is calculated."
	::= {mrmMonDummyPackage 2}

---
---	New Smart Packages for Repeater, Card and Port
---

mrmMonRepeaterTrafficLevel	OBJECT-TYPE
	SYNTAX			Counter
	ACCESS			read-only
	STATUS			mandatory
	DESCRIPTION
				"This is a smart MIB object which is used internally by the agent to
				provide a running average of the bandwidth in use. It should not be accessed by
				a management station and is used by the logic which calculates the value of
				its associated object 'mrmMonRepeaterBandwidthUsed'.

				See 'mrmMonRepeaterBandwidthUsed' for a description of how the bandwidth used
				is calculated."
	::= {mrmMonRepeaterSmartPackage 1}

mrmMonRepeaterErrorFrames	OBJECT-TYPE
	SYNTAX			Counter
	ACCESS			read-only
	STATUS			mandatory
	DESCRIPTION
				"This is a smart MIB object which is used internally by the agent to
				provide a running average of the error rate. It should not be accessed by a
				management station and is used by the logic which calculates the value of
				its associated object 'mrmMonRepeaterErrorsPer10000Packets'.

				See 'mrmMonRepeaterErrorsPer10000Packets' for a description of how the error rate
				is calculated."
	::= {mrmMonRepeaterSmartPackage 2}

mrmMonCardTrafficLevel	OBJECT-TYPE
	SYNTAX			Counter
	ACCESS			read-only
	STATUS			mandatory
	DESCRIPTION
				"This is a smart MIB object which is used internally by the agent to
				provide a running average of the bandwidth in use. It should not be accessed by
				a management station and is used by the logic which calculates the value of
				its associated object 'mrmMonCardBandwidthUsed'.

				See 'mrmMonCardBandwidthUsed' for a description of how the bandwidth used
				is calculated."
	::= {mrmMonCardSmartPackage 1}

mrmMonCardErrorFrames	OBJECT-TYPE
	SYNTAX			Counter
	ACCESS			read-only
	STATUS			mandatory
	DESCRIPTION
				"This is a smart MIB object which is used internally by the agent to
				provide a running average of the error rate. It should not be accessed by a
				management station and is used by the logic which calculates the value of
				its associated object 'mrmMonCardErrorsPer10000Packets'.

				See 'mrmMonCardErrorsPer10000Packets' for a description of how the error rate
				is calculated."
	::= {mrmMonCardSmartPackage 2}

mrmMonPortTrafficLevel	OBJECT-TYPE
	SYNTAX			Counter
	ACCESS			read-only
	STATUS			mandatory
	DESCRIPTION
				"This is a smart MIB object which is used internally by the agent to
				provide a running average of the bandwidth in use. It should not be accessed by
				a management station and is used by the logic which calculates the value of
				its associated object 'mrmMonPortBandwidthUsed'.

				See 'mrmMonPortBandwidthUsed' for a description of how the bandwidth used
				is calculated."
	::= {mrmMonPortSmartPackage 1}

mrmMonPortErrorFrames			OBJECT-TYPE
	SYNTAX			Counter
	ACCESS			read-only
	STATUS			mandatory
	DESCRIPTION
				"This is a smart MIB object which is used internally by the agent to
				provide a running average of the error rate. It should not be accessed by a
				management station and is used by the logic which calculates the value of
				its associated object 'mrmMonPortErrorsPer10000Packets'.

				See 'mrmMonPortErrorsPer10000Packets' for a description of how the error rate
				is calculated."
	::= {mrmMonPortSmartPackage 2}

-- **********************************************************************
-- Define enterprise repeater traps. Rules for mrm traps are that any
-- varbind must be from a table in which the first qualifier on the
-- object id is the service identifier of the 'thing' causing the trap.
-- **********************************************************************
repPartitionStateChange TRAP-TYPE
	ENTERPRISE a3Com
	VARIABLES   { mrmPortAutoPartitionState }
	DESCRIPTION "
This trap is sent when the partition state of a port changes. The trap
is accompanied by the new partition state of the port."
	::= 38

repLinkStateChange TRAP-TYPE
	ENTERPRISE a3Com
	VARIABLES   { mrmPortLinkState }
	DESCRIPTION "
This trap is sent when the link state of a port changes. The var-bind
identifies which port has changed state and what the new state of
that port is."
	::= 39

repAdminStateChange TRAP-TYPE
	ENTERPRISE a3Com
	VARIABLES   { mrmPortAdminStatus }
	DESCRIPTION "
This trap is only sent when the administration state of a port is changed
by a gauge. It is not sent if a user initiates a state change via SNMP,
Telnet or the V.24 terminal interface."
	::= 40

repPortTopUsage TRAP-TYPE
	ENTERPRISE	a3Com
        VARIABLES       {
                                mrmMonPortBandwidthUsed,
                                gaugeThresholdLevel,
                                gaugeSamplePeriod,
                                gaugeSamplesPerAverage
                        }
	DESCRIPTION "
This trap is sent when the port bandwidth used exceeds the defined
threshold. This threshold is by default 15%, although this may have been
changed on a particular device."
	::= 41

repPortErrors TRAP-TYPE
	ENTERPRISE	a3Com
        VARIABLES       {
                                mrmMonPortErrorsPer10000Packets,
                                gaugeThresholdLevel,
                                gaugeSamplePeriod,
                                gaugeSamplesPerAverage
                        }
	DESCRIPTION "
This trap is sent when the errors per packet exceeds the the defined
threshold."
	::= 42

dudUnauthorisedDevice           TRAP-TYPE
        ENTERPRISE a3Com
        VARIABLES   { mrmPortDUDAction }
        DESCRIPTION
                        "This trap is sent when an unrecognised MAC address appears on the port.
                        It is only sent if DUD is set on the port."

        ::= 66

repRepTopUsage TRAP-TYPE
	ENTERPRISE	a3Com
        VARIABLES       {
                                mrmMonRepBandwidthUsed,
                                gaugeThresholdLevel,
                                gaugeSamplePeriod,
                                gaugeSamplesPerAverage
                        }
	DESCRIPTION "
This trap is sent when the repeater bandwidth used exceeds the defined
threshold. This threshold is by default 15%, although this may have been
changed on a particular device."
	::= 67

repRepErrors TRAP-TYPE
	ENTERPRISE	a3Com
        VARIABLES       {
                                mrmMonRepErrorsPer10000Packets,
                                gaugeThresholdLevel,
                                gaugeSamplePeriod,
                                gaugeSamplesPerAverage
                        }
	DESCRIPTION "
This trap is sent when the repeater errors per packet exceeds the the defined
threshold."
	::= 68

repCardTopUsage TRAP-TYPE
	ENTERPRISE	a3Com
        VARIABLES       {
                                mrmMonCardBandwidthUsed,
                                gaugeThresholdLevel,
                                gaugeSamplePeriod,
                                gaugeSamplesPerAverage
                        }
	DESCRIPTION "
This trap is sent when the card bandwidth used exceeds the defined
threshold. This threshold is by default 15%, although this may have been
changed on a particular device."
	::= 69

repCardErrors TRAP-TYPE
	ENTERPRISE	a3Com
        VARIABLES       {
                                mrmMonCardErrorsPer10000Packets,
                                gaugeThresholdLevel,
                                gaugeSamplePeriod,
                                gaugeSamplesPerAverage
                        }
	DESCRIPTION "
This trap is sent when the errors per packet exceeds the the defined
threshold."
	::= 70
-- --------------------------------------------------------------------
-- *************************** SETUP GROUP ****************************
-- --------------------------------------------------------------------

	-- Implementation of the Setup group is mandatory for all
	-- Isolan systems.

	-- ----------------------------------------
	-- SETUP GENERAL GROUP
	-- ----------------------------------------

setupGeneral	OBJECT IDENTIFIER ::= { setup 1 }

	-- ----------------------------------------
	-- DEVICE HEARTBEAT
	-- ----------------------------------------

heartbeatInterval	OBJECT-TYPE
	SYNTAX	INTEGER (0..65535)
	ACCESS	read-write
	STATUS	mandatory
	DESCRIPTION
		"The time, in seconds, between successive heartbeat events
		sent to the management station.  An interval of 0 indicates
		that no heartbeat events are to be generated."
	::= { setupGeneral 1 }

heartbeatEvent 	TRAP-TYPE
	ENTERPRISE	a3Com
--	VARIABLES	{ }
	DESCRIPTION
		"Generated at a regular interval to inform the manager this
		device is still operating and can be reached on the network."
	::= 13

	-- ----------------------------------------
	-- Setup IP non-volatile configuaration
	-- ----------------------------------------

setupIp		OBJECT IDENTIFIER ::= { setup 2 }

setIpIfTable	OBJECT-TYPE
	SYNTAX	SEQUENCE OF SetIpIfEntry
	ACCESS	not-accessible
	STATUS	mandatory
	DESCRIPTION
		"This table shows the IP address and network mask to be used
		to initialise ipAddrTable on each network interface after the
		next system restart.  There is one entry per network interface
		and the index is equivalent to the index for the ifTable in
		the MIB-II interfaces group."
	::= { setupIp 1 }

setIpIfEntry	OBJECT-TYPE
	SYNTAX	SetIpIfEntry
	ACCESS	not-accessible
	STATUS	mandatory
	DESCRIPTION
		"The default information relating to a single IP interface."
	INDEX	{ setIpIfIndex }
	::= { setIpIfTable 1 }

	SetIpIfEntry ::= SEQUENCE {
		setIpIfIndex	INTEGER,
		setIpIfAddr	IpAddress,
		setIpIfMask	IpAddress
		}

setIpIfIndex	OBJECT-TYPE
	SYNTAX	INTEGER
	ACCESS	read-only
	STATUS	mandatory
	DESCRIPTION
		"The index value which uniquely identifies the
		interface to which this entry is applicable.  The
		interface identified by a particular value of this
		index is the same interface as identified by the
		same value of ifIndex (for ifTable)."
	::= { setIpIfEntry 1 }

setIpIfAddr	OBJECT-TYPE
	SYNTAX	IpAddress
	ACCESS	read-write
	STATUS	mandatory
	DESCRIPTION
		"The IP address to be used for this interface."
	::= { setIpIfEntry 2 }

setIpIfMask	OBJECT-TYPE
	SYNTAX	IpAddress
	ACCESS	read-write
	STATUS	mandatory
	DESCRIPTION
		"The IP network mask to be used for this interface."
	::= { setIpIfEntry 3 }

setIpIfRouter	OBJECT-TYPE
	SYNTAX	IpAddress
	ACCESS	read-write
	STATUS	mandatory
	DESCRIPTION
		"This is the IP address of the default router to be used for
		sending IP datagrams to remote destinations which have no
		suitable entry in the routing table.  This corresponds to an
		entry in the MIB-II ipRouteTable with an ipRouteDest field of
		'0.0.0.0' (the default router) which is set up from this value
		after a system restart.

		Changes to this value do not affect the IP routing table until
		after the next system restart.  (To change the default router
		without a restart, the IP routing table should be changed
		directly, with an equivalent change to setIpIfRouter only if
		the change is required to be made permanently.)"
	::= { setupIp 2 }

	-- ----------------------------------------
	-- Device Start-up Data
	-- ----------------------------------------

setupStart	OBJECT IDENTIFIER ::= { setup 3 }

startPROMSwVerNo	OBJECT-TYPE
	SYNTAX	DisplayString (SIZE (1..16))
	ACCESS	read-only
	STATUS	mandatory
	DESCRIPTION
		"The PROM software version number."
	::= { setupStart 1 }

startRestartCount	OBJECT-TYPE
	SYNTAX	Counter
	ACCESS	read-only
	STATUS	mandatory
	DESCRIPTION
		"The number of restarts the box has undergone, either power
		on or reset switch or watchdog expiries."
	::= { setupStart 2 }

startLastRestartType	OBJECT-TYPE
	SYNTAX	INTEGER {
		other		(1),
		command		(2),
		watchdog	(3),
		power-reset	(4),
		system-error	(5)
		}
	ACCESS	read-only
	STATUS	mandatory
	DESCRIPTION
		"The reason for the last system restart.  This may be due to
		management command; watchdog timeout expiry; power
		interruption; the reset switch was pressed or system error.  It is not
		possible to differentiate between the latter two causes."
	::= { setupStart 3 }

startResetAction	OBJECT-TYPE
	SYNTAX	INTEGER {
		nochange	(1),
		manDefaultReset	(2)
		}
	ACCESS	read-write
	STATUS	mandatory
	DESCRIPTION
		"Reset the device with
		manufacturers default configuration if the manDefaultReset
		value is written to this item."
	::= { setupStart 4 }

startLastSystemError	OBJECT-TYPE
	SYNTAX	INTEGER
	ACCESS	read-only
	STATUS	mandatory
	DESCRIPTION
		"The last System Error experienced by the system. This is set
		 to the NVRAM last system error code on startup. When the system
		 issues a TRAP indicating the last system error number the NVRAM
		 version is set to zero. Hence after the next restart this
		 attribute will have the value zero also."
	::= { setupStart 5 }

startRestartAction	OBJECT-TYPE
	SYNTAX	INTEGER {
		nochange	(1),
		restart		(2)
		}
	ACCESS	read-write
	STATUS	mandatory
	DESCRIPTION
		"Restart the device with it's current configuration if the restart
		value is written to this item."
	::= { setupStart 6 }

-- --------------------------------------------------------------------
-- *********************** SYSTEM LOADER GROUP ************************
-- --------------------------------------------------------------------

loadableDeviceTable     OBJECT-TYPE
	SYNTAX		SEQUENCE OF LoadableDeviceEntry
	ACCESS		not-accessible
	STATUS		mandatory
	DESCRIPTION
		"A table which is used to control the loading of new software
		images to the devices controlled by the management agent.
		By convention the first entry in the table (device type =
		system(1), instance = 1) controls the loading of the device
		containing the management agent itself. Agents which have
		no subsidiary devices will have only this one entry in the
		table.  If the Agent does control subsidiary devices, the other
		entries control the loading of software into subsidiary devices."
	::= { sysLoader 1 }

loadableDeviceEntry	OBJECT-TYPE
	SYNTAX		LoadableDeviceEntry
	ACCESS		not-accessible
	STATUS		mandatory
	DESCRIPTION
		"An entry containing the objects for controlling the loading
		of a software image to a device controlled by the agent."
	INDEX		{ slDeviceType, slDeviceInstance }
	::= { loadableDeviceTable 1 }

LoadableDeviceEntry ::= SEQUENCE {
	slDeviceType
		INTEGER,
	slDeviceInstance
		INTEGER,
	slLoadStatus
		INTEGER,
	slSoftwareVersion
		DisplayString,
	slHardwareVersion
		INTEGER,
	slFilename
		DisplayString,
	slServerIpAddress
		IpAddress,
	slLoad
		INTEGER,
	slServerAddress
		DisplayString,
	slServerProtocol
		INTEGER
}

slDeviceType		OBJECT-TYPE
	SYNTAX		INTEGER {
			    system(1),
			    component(2)
			}
	ACCESS		read-only
	STATUS		mandatory
	DESCRIPTION
		"The type of the device to load.  Simple agents only contain
		one device type, which is always `system'.  More complex
		agents, probably containing multiple processors, may contain
		subsidiary devices denoted (for the purposes of the system
		loader) as `component'.  In general, a `system' device is one
		which monitors and/or manages the operation of `component'
		devices."
	::= { loadableDeviceEntry 1 }

slDeviceInstance	OBJECT-TYPE
	SYNTAX		INTEGER
	ACCESS		read-only
	STATUS		mandatory
	DESCRIPTION
		"The instance of the device type specified by slDeviceType.
		By convention instance 1 of the system devices is the one
		containing the management agent, and always exists.
		Many systems will contain only the one instance of the system
		device type."
	::= { loadableDeviceEntry 2 }

slLoadStatus		OBJECT-TYPE
	SYNTAX		INTEGER {
			    fileNotFound(1),
			    accessViolation(2),
			    illegalOperation(4),
			    unknownTransferID(5),
			    noSuchUser(7),
			    noResponse(8),
			    noResource(9),
			    recLenMismatch(10),
			    invalidRecType(11),
			    checksumError(12),
			    wrongDevice(13),
			    wrongHardwareVersion(14),
			    noFileHeader(15),
			    byteCountError(16),
			    invalidProgAddress(17),
			    eraseFailed(18),
			    progFailed(19),
			    loadPending(20),
			    loadActive(21),
			    success(22),
			    paused(23),
			    modInvalidAdress(200),
			    modChecksumError(201),
			    modTimeout(202),
			    modBusy(203),
			    modRemoved(204),
			    modNoResource(205),
			    modFailure(255)
			}
	ACCESS		read-only
	STATUS		mandatory
	DESCRIPTION
			"The status of the last system load operation requested
			for this device.  If the value of this object is in the
			range 1 to 19 inclusive, or 200 or more, the download
			failed, and the value is an error code indicating the
			reason why.  Codes 1 to 7 are a direct mapping from the
			TFTP error codes defined in RFC-783.  The possible
			status values and their meanings are as follows:-
			    fileNotFound(1)
				the server cannot find the requested file;
			    accessViolation(2)
				the file system security mechanism does not
				permit TFTP to access the requested file;
			    illegalOperation(4)
				TFTP protocol error;
			    unknownTransferID(5)
				TFTP protocol error;
			    noSuchUser(7)
				user number not recognised;
			    noResponse(8)
				load server failed to respond;
			    noResource(9)
				the download could not be started because of a
				lack of resources;
			    recLenMismatch(10)
				the record length differs from that implied
				by the value of the record length field;
			    invalidRecType(11)
				the record type is not recognised;
			    checksumError(12)
				record checksum error;
			    wrongDevice(13)
				the device type in the file is incorrect;
			    wrongHardwareVersion(14)
				the software image is not suitable for this
				version of the hardware;
			    noFileHeader(15)
				the first record in the file was not a file
				header;
			    byteCountError(16)
				the byte count reported in the file trailer
				record differed from the number of bytes
				actually received;
			    invalidProgAddress(17)
				the load file contained a load address which
				was outside the valid range of memory;
			    eraseFailed(18)
				unable to erase the program memory;
			    progFailed(19)
				hardware error programming the memory.
			The meanings of the remaining values are as follows:-
			    loadPending(20)
				a load has been requested but has not yet begun;
			    loadActive(21)
				the device is currently being downloaded;
			    success(22)
				the device has been downloaded successfully;
			    paused(23)
				the device could not complete the download at
				this time, it will request that the load be
				restarted when it is ready.
			The following status values may result from downloading
			a subsidiary module:-
			    modInvalidAdress(200)
				the load file contained a load address which
				was outside the valid range of memory;
			    modChecksumError(201)
				the load data was corrupted as it was
				transferred from the management agent to the
				subsidiary module;
			    modTimeout(202)
				the management agent timed out while waiting
				for a response from the subsidiary module;
			    modBusy(203)
				the subsidiary module was unable to accept a
				command from the management agent;
			    modRemoved(204)
				the subsidiary module was removed during the
				download;
			    modNoResource(205)
				the download could not continue because of a
				lack of resources;
			    modFailure(255)
				the subsidiary module failed during the
				download."
	DEFVAL		{ success }
	::= { loadableDeviceEntry 3 }

slSoftwareVersion	OBJECT-TYPE
	SYNTAX		DisplayString(SIZE(0..32))
	ACCESS		read-only
	STATUS		mandatory
	DESCRIPTION
		"The version identifier of the software running in the device."
	::= { loadableDeviceEntry 4 }

slHardwareVersion	OBJECT-TYPE
	SYNTAX		INTEGER
	ACCESS		read-only
	STATUS		mandatory
	DESCRIPTION
		"The version number identifying the revision level of the
		hardware of the device"
	::= { loadableDeviceEntry 5 }

slFilename		OBJECT-TYPE
	SYNTAX		DisplayString(SIZE(1..128))
	ACCESS		read-write
	STATUS		mandatory
	DESCRIPTION
		"The name of the file which contains the software image to
		load, or which was the last loaded to the device."
	::= { loadableDeviceEntry 6 }

slServerIpAddress	OBJECT-TYPE
	SYNTAX		IpAddress
	ACCESS		read-write
	STATUS		deprecated
	DESCRIPTION
		"The IP address of the host containing the software image to
		load, or from which the last image loaded was read.

		This object has been deprecated in favour of writing the IP address
		into slServerAddress."
	DEFVAL		{ 0 }
	::= { loadableDeviceEntry 7 }

slLoad			OBJECT-TYPE
	SYNTAX		INTEGER {
			    noAction(1),
			    startDownload(2)
			}
	ACCESS		write-only
	STATUS		mandatory
	DESCRIPTION
		"Writing 2 to this object causes the agent to attempt to
		load a new software image to the corresponding device.  The
		file to load and the address of the server to load it
		from are specified in the other objects in the same row of
		the table."
	::= { loadableDeviceEntry 8 }

slServerAddress	OBJECT-TYPE
	SYNTAX		DisplayString (SIZE(0..50))
	ACCESS		read-write
	STATUS		mandatory
	DESCRIPTION
		"The address of the server containing the software image to
		load, or from which the last image was loaded.

		This is either an IP address in standard dotted notation, or
		an IPX address in the format aabbccdd:112233445566. An error
		is returned if the agent does not support the download protocol
		implied by the address format."
	::= { loadableDeviceEntry 9 }

slServerProtocol OBJECT-TYPE
	SYNTAX		INTEGER { unknown(1), tftp-ip(2), tftp-ipx(3) }
	ACCESS		read-only
	STATUS		mandatory
	DESCRIPTION
		"This is the protocol to use when downloading the software from the
		server specified in slServerAddress.

		At present, this value is determined by the value of slServerAddress
		which is currently un-ambiguous and so this object is read-only."
	DEFVAL	{ unknown }
	::= { loadableDeviceEntry 10 }

	-- ----------------------------------------
	--	System Loader Trap
	-- ----------------------------------------

slFailed		TRAP-TYPE
	ENTERPRISE  	a3Com
	VARIABLES   	{ slLoadStatus }
	DESCRIPTION
		"When a system load is requested, a response is returned
		immediately and the load proceeds in the background.  If an
		error is detected this trap is generated indicating the
		reason why in the status, as follows:-
		     (1) file not found;
		     (2) access violation;
		     (4) illegal TFTP operation;
		     (5) unknown transfer ID;
		     (7) no such user;
		     (8) no response from the load server;
		     (9) the download could not be started because of a
			 lack of resources;
		    (10) the length of a record differs from that implied
			 by the value of the record length field;
		    (11) the record type is not recognised;
		    (12) record checksum error;
		    (13) the device type in the file is incorrect;
		    (14) the software image is not suitable for this
			 version of the hardware;
		    (15) the first record in the file was not a file
			 header;
		    (16) The byte count reported in the file trailer
			 record differed from the number of bytes
			 actually received;
		   (200) the load file contained a load address which
			 was outside the valid range of memory;
		   (201) the load data was corrupted as it was
			 transferred from the management agent to the
			 subsidiary module;
		   (202) the management agent timed out while waiting
			 for a response from the subsidiary module;
		   (203) the subsidiary module was unable to accept a
			 command from the management agent;
		   (204) the subsidiary module was removed during the
			 download;
		   (205) the download could not continue because of a
			 lack of resources;
		   (255) the subsidiary module failed during the
			 download.
		When loading a new image into the device containing the agent
		itself,  the agent first reads the beginning of the image
		file to test if it is accessible and contains a valid image.
		If there is anything wrong, this trap is generated, no
		download is performed and the device continues to run
		uninterrupted.  If this check is successful the download
		proper is begun.  Should that fail, it is simply retried
		continuously until either an attempt succeeds or the
		device is reset."
	::= 18

-- --------------------------------------------------------------------
-- ************************ SECURITY GROUP ****************************
-- --------------------------------------------------------------------

	-- Implementation of the Security group is mandatory for all
	-- Isolan systems.

	-- ----------------------------------------
	-- SECURITY ENABLE TABLE
	-- ----------------------------------------

securityEnableTable	OBJECT-TYPE
	SYNTAX	SEQUENCE OF SecurityEnableTableEntry
	ACCESS	not-accessible
	STATUS	mandatory
	DESCRIPTION
		"A table of permissions for access to the managed device
		from each of its interfaces, at each security access level.
		The table is fixed at 5 rows, indexed by the access level."
	::= { security 1 }

securityEnableTableEntry	OBJECT-TYPE
	SYNTAX	SecurityEnableTableEntry
	ACCESS	not-accessible
	STATUS	mandatory
	DESCRIPTION
		"This table allows individual interfaces to be enabled
		or disabled separately for each security level."
	INDEX	{ securityLevel }
	::= { securityEnableTable 1 }

	SecurityEnableTableEntry ::= SEQUENCE {
		securityLevel			INTEGER,
		securityCommunityEnable		INTEGER,
		securitySecureEnable		INTEGER,
		securityTermEnable		INTEGER,
		securityTelnetEnable		INTEGER,
		securityFrontPanelEnable	INTEGER
	}

securityLevel	OBJECT-TYPE
	SYNTAX	INTEGER {
		monitor(1),
		secureMonitor(2),
		manager(3),
		specialist(4),
		security(5)
	}
	ACCESS	read-only
	STATUS	mandatory
	DESCRIPTION
		"Index to the security enable table."
	::= { securityEnableTableEntry 1 }

securityCommunityEnable	OBJECT-TYPE
	SYNTAX	INTEGER {
		enable(1),
		disable(2),
		permanentlyEnabled(3),
		permanentlyDisabled(4)
		}
	ACCESS	read-write
	STATUS	mandatory
	DESCRIPTION	"Community SNMP access permission"
	::= { securityEnableTableEntry 2 }

securitySecureEnable	OBJECT-TYPE
	SYNTAX	INTEGER {
		enable(1),
		disable(2),
		permanentlyEnabled(3),
		permanentlyDisabled(4)
		}
	ACCESS	read-write
	STATUS	mandatory
	DESCRIPTION	"Secure SNMP access permission"
	::= { securityEnableTableEntry 3 }

securityTermEnable	OBJECT-TYPE
	SYNTAX INTEGER {
		enable(1),
		disable(2),
		permanentlyEnabled(3),
		permanentlyDisabled(4)
		}
	ACCESS	read-write
	STATUS	mandatory
	DESCRIPTION	"Local Terminal access permission"
	::= { securityEnableTableEntry 4 }

securityTelnetEnable	OBJECT-TYPE
	SYNTAX INTEGER {
		enable(1),
		disable(2),
		permanentlyEnabled(3),
		permanentlyDisabled(4)
		}
	ACCESS	read-write
	STATUS	mandatory
	DESCRIPTION	"Telnet access permission"
	::= { securityEnableTableEntry 5 }

securityFrontPanelEnable	OBJECT-TYPE
	SYNTAX INTEGER {
		enable(1),
		disable(2),
		permanentlyEnabled(3),
		permanentlyDisabled(4)
		}
	ACCESS	read-write
	STATUS	mandatory
	DESCRIPTION	"Front Panel access permission"
	::= { securityEnableTableEntry 6 }

	-- ----------------------------------------
	-- The Local device USER TABLE
	-- ----------------------------------------

securityUserTable	 OBJECT-TYPE
	SYNTAX	SEQUENCE OF SecurityUserTableEntry
	ACCESS	not-accessible
	STATUS	mandatory
	DESCRIPTION	"A table used to define Users.
		Users can be created/modified or deleted, with the
		exception of the default Users which cannot
		be deleted."
	::= { security 2 }

securityUserTableEntry	OBJECT-TYPE
	SYNTAX	SecurityUserTableEntry
	ACCESS	not-accessible
	STATUS	mandatory
	DESCRIPTION
		"1. Creating a new user is done by using the username as
		a qualifier and SETting any of the items in the row -
		defaults will be used for the remaining values.
		2. Deleting a user is by writing 'invalid' to the status
		column.
		3. There must always be users called 'monitor', 'manager'
		and 'security' - these cannot be deleted."
	INDEX	{ securityUserName }
	::= { securityUserTable 1 }

	SecurityUserTableEntry ::= SEQUENCE {
		securityUserStatus	INTEGER,
		securityUserName	DisplayString,
		securityUserLevel	INTEGER,
		securityUserPassword	DisplayString,
		securityUserCommunity	DisplayString,
		securityUserLocParty	OBJECT IDENTIFIER,
		securityUserMgrParty	OBJECT IDENTIFIER
	}

securityUserStatus	OBJECT-TYPE
	SYNTAX	INTEGER {
		valid(1),
		invalid(2)
		}
	ACCESS	read-write
	STATUS	mandatory
	DESCRIPTION
		"User Status.  `invalid' is used to indicate this user
		is no longer allowed to access this device, and the
		table entry may subsequently be re-used. Note that
		the Status of default Users cannot be set to invalid."
	::= { securityUserTableEntry 1 }

securityUserName	OBJECT-TYPE
	SYNTAX	DisplayString (SIZE (1..10))
	ACCESS	read-only
	STATUS	mandatory
	DESCRIPTION
		"An ASCII string for the User Name.  Empty strings are
		not allowed.  The index column for the User Table."
	::= { securityUserTableEntry 2 }

securityUserLevel	OBJECT-TYPE
	SYNTAX	INTEGER {
		monitor(1),
		secureMonitor(2),
		manager(3),
		specialist(4),
		security(5)
		}
	ACCESS	read-write
	STATUS	mandatory
	DESCRIPTION
		"User Access Level defining the scope of management allowed
		for this user.  Note that the access level of default Users
		cannot be changed."
	::= { securityUserTableEntry 3 }

securityUserPassword	OBJECT-TYPE
	SYNTAX	DisplayString (SIZE (0..10))
	ACCESS	write-only
	STATUS	mandatory
	DESCRIPTION
		"The password required for user confirmation, when access
		is made via the local serial port, the front panel,
		or via Telnet."
	::= { securityUserTableEntry 4 }

securityUserCommunity	 OBJECT-TYPE
	SYNTAX	DisplayString (SIZE (0..32))
	ACCESS	read-write
	STATUS	mandatory
	DESCRIPTION
		"The community string identifying this user, when access
		is made via the original community-based SNMP (RFC1157)."
	::= { securityUserTableEntry 5 }

securityUserLocParty	 OBJECT-TYPE
	SYNTAX	OBJECT IDENTIFIER
	ACCESS	read-write
	STATUS	mandatory
	DESCRIPTION
		"The local party identity of this user, when access
		is made via secure SNMP."
	::= { securityUserTableEntry 6 }

securityUserMgrParty	 OBJECT-TYPE
	SYNTAX	OBJECT IDENTIFIER
	ACCESS	read-write
	STATUS	mandatory
	DESCRIPTION
		"The manager party identity for this user, when access
		is made via secure SNMP."
	::= { securityUserTableEntry 7 }
-- 
	-- ----------------------------------------
	--	AUDIT LOG
	-- ----------------------------------------

securityAuditLogTable	OBJECT-TYPE
	SYNTAX	SEQUENCE OF SecurityAuditLogEntry
	ACCESS	not-accessible
	STATUS	mandatory
	DESCRIPTION
		"The audit log is a circular table recording all updates to
		the managed database on the device.  The log must be read
		regularly by a management device, to maintain a more
		permanent record of the management history."
	::= { security 3 }

securityAuditLogEntry	OBJECT-TYPE
	SYNTAX	SecurityAuditLogEntry
	ACCESS	not-accessible
	STATUS	mandatory
	DESCRIPTION
		"Each entry contains the time an update was made, by whom,
		the item referenced, the new value and the result of this
		request."
	INDEX	{ securityAuditIndex }
	::= { securityAuditLogTable 1 }

	SecurityAuditLogEntry ::= SEQUENCE {
		securityAuditIndex	INTEGER,
		securityAuditTime	TimeTicks,
		securityAuditUser	DisplayString,
		securityAuditObject	OBJECT IDENTIFIER,
		securityAuditValue	OCTET STRING,
		securityAuditResult	INTEGER
	}

securityAuditIndex	OBJECT-TYPE
	SYNTAX	INTEGER (1..65535)
	ACCESS	read-only
	STATUS	mandatory
	DESCRIPTION
		"Audit Log Index.  A monotonically increasing value to
		uniquely identify an entry in the audit log.  This value
		wraps around (to 1) after reaching the maximum value (65535)."
	::= { securityAuditLogEntry 1 }

securityAuditTime	OBJECT-TYPE
	SYNTAX	TimeTicks
	ACCESS	read-only
	STATUS	mandatory
	DESCRIPTION
		"The time, in hundredths of a second since the last system
		restart, of the update request."
	::= { securityAuditLogEntry 2 }

securityAuditUser	OBJECT-TYPE
	SYNTAX	DisplayString (SIZE (0..10))
	ACCESS	read-only
	STATUS	mandatory
	DESCRIPTION	"The name of the user making the request."
	::= { securityAuditLogEntry 3 }

securityAuditObject	OBJECT-TYPE
	SYNTAX	OBJECT IDENTIFIER
	ACCESS	read-only
	STATUS	mandatory
	DESCRIPTION
		"The object identifier of the item being updated.  This
		includes any qualifier for the item."
	::= { securityAuditLogEntry 4 }

securityAuditValue	OBJECT-TYPE
	SYNTAX	OCTET STRING (SIZE (0..200))
	ACCESS	read-only
	STATUS	mandatory
	DESCRIPTION	"The new value for the item."
	::= { securityAuditLogEntry 5 }

securityAuditResult	OBJECT-TYPE
	SYNTAX	INTEGER {
		success(255),		-- update succeeded
		pending(1),		-- update not yet completed
		too-big(2),		-- value rejected as too big for item
		failed(3),		-- value rejected by access function
		locked(4),		-- item is locked by another manager
		security-violation(5),	-- user does not have correct
					--	access level
		no-such-function(6),	-- item is read-only
		no-such-item(7)		-- item does not exist
	}
	ACCESS	read-only
	STATUS	mandatory
	DESCRIPTION
		"The result of the update request may indicate that it was
		applied successfully, that it failed (for one of a number of
		reasons) or that it is still in progress."
	::= { securityAuditLogEntry 6 }

-- --------------------------------------------------------------------
--			END OF SECURITY GROUP
-- --------------------------------------------------------------------

-- --------------------------------------------------------------------
-- ************************ GAUGES GROUP ****************************
-- --------------------------------------------------------------------

	-- Implementation of the Gauges group is optional for all
	-- Isolan systems.

	-- ----------------------------------------
	-- GAUGE TABLE
	-- ----------------------------------------

gaugeTable	OBJECT-TYPE
	SYNTAX	SEQUENCE OF GaugeTableEntry
	ACCESS	not-accessible
	STATUS	mandatory
	DESCRIPTION	"A table used to define Alarms."
	::= { gauges 1 }

gaugeTableEntry	OBJECT-TYPE
	SYNTAX	GaugeTableEntry
	ACCESS	not-accessible
	STATUS	mandatory
	DESCRIPTION
		"This table allows Alarms to be set-up on items in the MIB."
	INDEX	{ gaugeIndex }
	::= { gaugeTable 1 }

	GaugeTableEntry ::= SEQUENCE {
		gaugeIndex		INTEGER,
		gaugeItemId		OBJECT IDENTIFIER,
		gaugeItemType		INTEGER,
		gaugeSamplesPerAverage	INTEGER,
		gaugeSamplePeriod	INTEGER,
		gaugeValue		INTEGER,
		gaugePeakValue		INTEGER,
		gaugeThresholdLevel	INTEGER,
		gaugeRecoveryLevel	INTEGER,
		gaugeThresholdAction	INTEGER,
		gaugeRecoveryAction	INTEGER,
		gaugeState		INTEGER,
		gaugeOwner		DisplayString
	}

gaugeIndex	OBJECT-TYPE
	SYNTAX	INTEGER
	ACCESS	read-only
	STATUS	mandatory
	DESCRIPTION
		"Unique identifier for a row in the Alarm Table.  Allocated by
		 the Alarms Subsystem.  An integer in the range
		 1..gaugeTableSize."
	::= { gaugeTableEntry 1 }

gaugeItemId	OBJECT-TYPE
	SYNTAX	OBJECT IDENTIFIER
	ACCESS	read-write
	STATUS	mandatory
	DESCRIPTION
		"The object Id and qualifier of the item to be monitored by
		this alarm. "
	::= { gaugeTableEntry 2 }

gaugeItemType	OBJECT-TYPE
	SYNTAX	INTEGER	{
			counter (1),
			signedMeter (2),
			unsignedMeter (3)
			}
	ACCESS	read-write
	STATUS	mandatory
	DESCRIPTION
		"A 'counter', by definition will always be a positive number.
		'Meters' can be signed or unsigned."
	::= { gaugeTableEntry 3 }

gaugeSamplesPerAverage	OBJECT-TYPE
	SYNTAX	INTEGER	{
			nonAveraging (1),
			twoSamples (2),
			threeSamples (3),
			maxSamples (4)
			}
	ACCESS	read-write
	STATUS	mandatory
	DESCRIPTION
		"The number of samples used to calculate the Alarm Value. The
		default number of samples is four. If a SamplesPerAverage value
		of one is used, no average is calculated and the GaugeValue
		will be the most recent sample."
	::= { gaugeTableEntry 4 }

gaugeSamplePeriod	OBJECT-TYPE
	SYNTAX	INTEGER	(1..4294967295)
	ACCESS	read-write
	STATUS	mandatory
	DESCRIPTION
		"Number of seconds between samples. The total averaging period
		is given by (gaugeSamplesPerAverage * gaugeSamplePeiod) secs."
	::= { gaugeTableEntry 5 }

gaugeValue	OBJECT-TYPE
	SYNTAX	INTEGER	(0..4294967295)
	ACCESS	read-write
	STATUS	mandatory
	DESCRIPTION
		"The most recently computed average of the item being
		monitored. For a `meter' alarm, this is the simple average of
		the samples. For a 'counter' alarm, this is the average of the
		differences between successive samples. Counters and
		unsignedMeters are unsigned 32-bit values and have a maximum
		value of 4294967295. signedMeters are signed 32-bit values and
		have a maximum value of +-2147483647 divided by the value of
		gaugeSamplesPerAverage ."
	::= { gaugeTableEntry 6 }

gaugePeakValue	OBJECT-TYPE
	SYNTAX	INTEGER	(0..4294967295)
	ACCESS	read-write
	STATUS	mandatory
	DESCRIPTION
		"The highest recorded Alarm Value. This will be either a
		signed or unsigned 32 bit value depending on the gaugeItemType"
	::= { gaugeTableEntry 7 }

gaugeThresholdLevel	OBJECT-TYPE
	SYNTAX	INTEGER	(0..4294967295)
	ACCESS	read-write
	STATUS	mandatory
	DESCRIPTION	"The threshold value of the the Alarm which causes the
			ThresholdState to move from the 'ready' state to the
			'fired' state and also causes the the ThresholdAction
			to be taken. It will be either a signed or unsigned
			32-bit integer depending on the gaugeItemType."
	::= { gaugeTableEntry 8 }

gaugeRecoveryLevel	OBJECT-TYPE
	SYNTAX	INTEGER
	ACCESS	read-write
	STATUS	mandatory
	DESCRIPTION
		"The threshold value of the the Alarm which causes the
		ThresholdState to move from the `fired' state to the `ready'
		state and also causes the the RecoveryAction to be taken. This
		value will be either a signed or unsigned 32-bit integer
		depending on the gaugeItemType."
	::= { gaugeTableEntry 9 }

gaugeThresholdAction	OBJECT-TYPE
	SYNTAX	INTEGER	{
			noAction (1),
			sendTrap (2),	-- Send a Trigger event to manager
			disable (3),	-- e.g. turn off port
			enable (4),	-- e.g. turn on port
			notifyAndBlipPortOff (5),
			notifyAndBlipCardOff (6),
			notifyAndDisablePort (8),
			notifyAndDisableCard (9),
			blipPortOff (12),
			blipCardOff (13),
			disablePort (14),
			disableCard (15),
			notifyAndResilientSwitch (18),
			notifyBandwidthExceeded (19),
			notifyErrorsExceeded (20),
			notifyPollFailed (22),
			notifyFilterBridgePort (23)
			}
	ACCESS	read-write
	STATUS	mandatory
	DESCRIPTION
		"This object identifies the action to be taken when an Alarm
		crosses the Threshold Level. The default action will be to send
		a trigger event (sendTrap). The other actions are device
		specific and may not be available on all devices. See the RMON
		Event Table for the actions supported by this device."
	::= { gaugeTableEntry 10 }

gaugeRecoveryAction	OBJECT-TYPE
	SYNTAX	INTEGER	{
			noAction (1),
			sendTrap (2),	-- Send a Trigger event to manager
			disable (3),	-- e.g. turn off port
			enable (4),	-- e.g. turn on port
			notifyAndEnablePort (10),
			notifyAndEnableCard (11),
			enablePort (16),
			enableCard (17),
			notifyPollSuccess (21),
			notifyUnfilterBridgePort (24)
			}
	ACCESS	read-write
	STATUS	mandatory
	DESCRIPTION
		"This object identifies the action to be taken when a 'fired'
		Alarm crosses the Recovery Level. The default action will be
		to send a recovery event (sendTrap). The actions for 'disable'
		and 'enable' are device specific."
	::= { gaugeTableEntry 11 }

gaugeState	OBJECT-TYPE
	SYNTAX	INTEGER	{
			onTriggersEnabled (1),
			onTriggersDisabled (2),
			off (3),
			deleted (4),
			autoCalibrate(5)
			}
	ACCESS	read-write
	STATUS	mandatory
	DESCRIPTION
		"
		onTriggersEnabled 	- This is the normal active state of a
		alarm. The gaugeValue is updated on every sample and if it
		crosses the Threshold or Recovery Levels, the corresponding
		Action will be taken.

		onTriggersDisabled	- This is used when a new device, or
		alarm is set up and the Threshold and Recovery Levels have not
		been calibrated.  The Alarm runs as normal and the gaugeValue
		and peakValue are updated. However, if the gaugeValue crosses
		the Threshold or Recovery Levels, no action is taken.

		off	- This de-activates the alarm, allowing it to be
		configured safely . Before updating any of the Alarm fields
		the alarm SHOULD be turned off. Turning the alarm 'off' and
		then 'on' will not lose any of the sampling data, gaugeValue,
		peakValue, or thresholdStatus. Updates to the index fields
		will fail since they are read-only.

		deleted	- An alarm is invalidated by setting it to 'deleted'.
		A 'deleted' alarm will not be returned by a 'GetNext' request.

		autoCalibrate	- Updates the Threshold and Recovery
		values according to the current peak value. The gaugeState
		will then be set to 'onTriggersEnabled'. This can be done
		when the gaugeState is in states (1), (2), or (3).
		After this operation:

			thresholdLevel 	= peakValue * %gaugeThresholdLevelScaler
			recoveryLevel  	= peakValue * %gaugeRecoveryLevelScaler
			gaugeState	= onTriggersEnabled

		When the gaugeState is set to either of the 'on' states, all
		the fields for the Alarm are validated. If any of the fields
		are invalid, the operation will fail.

		The sampling data, gaugeValue, peakValue and thresholdState
		can be reset by writing 'onTriggersEnabled', 'onTriggers-
		Disabled' , or 'autoCalibrate' to the gaugeState when it is
		already in either of the 'on' states."
	::= { gaugeTableEntry 12 }

       gaugeOwner OBJECT-TYPE
              SYNTAX DisplayString
              ACCESS read-write
              STATUS mandatory
              DESCRIPTION
                  "The entity that configured this entry and is
                  therefore using the resources assigned to it."
              ::= { gaugeTableEntry 13 }

gaugeTableSize	OBJECT-TYPE
	SYNTAX	INTEGER	(1..65535)
	ACCESS	read-only
	STATUS	mandatory
	DESCRIPTION
		"Number of entries in Alarm Table. The size of the Alarm Table
		depends on the requirements and available resources of the
		device. The actual maximum will probably be around 1000."
	::= { gauges 2 }

gaugeThresholdLevelScaler	OBJECT-TYPE
	SYNTAX	INTEGER	(1..65535)
	ACCESS	read-write
	STATUS	mandatory
	DESCRIPTION
		"The ThresholdLevel is set to this percentage of the peakValue
		when the Alarm is auto-calibrated.

		e.g	gaugeThresholdLevelScaler = 120
			gaugePeakValue = 360

			After writing 'calibrateTriggers' to the gaugeState:

			ThresholdLevel = 120/100 * 360
				       = 432"
	::= { gauges 3 }

gaugeRecoveryLevelScaler	OBJECT-TYPE
	SYNTAX	INTEGER	(1..65535)
	ACCESS	read-write
	STATUS	mandatory
	DESCRIPTION
		"The RecoveryLevel is set to this percentage of the peakValue
		when the Alarm is auto-calibrated.

		e.g	gaugeRecoveryLevelScaler = 90
			gaugePeakValue = 360

			After writing 'calibrateTriggers' to the gaugeState:

			RecoveryLevel = 90/100 * 360
				      = 324"
	::= { gauges 4 }

gaugeTableUpdate	OBJECT-TYPE
	SYNTAX	INTEGER	{
			deleteAll (1)	-- Set all Alarms to 'deleted'
			}
	ACCESS	write-only
	STATUS	mandatory
	DESCRIPTION
		"Performs the specified operation on every Alarm in the table."
	::= { gauges 5 }

gaugeConfigureObjId	OBJECT-TYPE
	SYNTAX	OBJECT IDENTIFIER
	ACCESS	write-only
	STATUS	mandatory
	DESCRIPTION
		"Object Id and qualifier of alarm(s) to be updated."
	::= { gauges 6 }

gaugeConfigureColumn	OBJECT-TYPE
	SYNTAX	INTEGER {
			itemType(1),
			samplesPerAverage(2),
			samplePeriod(3),
			thresholdLevel(4),
			recoveryLevel(5),
			thresholdAction(6),
			recoveryAction(7),
			gaugeState(8)
			}
	ACCESS	write-only
	STATUS	mandatory
	DESCRIPTION
		"Alarm Table Column to be updated."
	::= { gauges 7 }

gaugeConfigureValue	OBJECT-TYPE
	SYNTAX	INTEGER (1..4294967295)
	ACCESS	write-only
	STATUS	mandatory
	DESCRIPTION
		"Value to be written to the 'gaugeConfigureColumn' of the
		Alarms which match the 'gaugeConfigureObjId'. Writing to this
		value initiates the operation."
	::= { gauges 8 }

gaugeNextFreeIndex	OBJECT-TYPE
	SYNTAX	INTEGER
	ACCESS	read-only
	STATUS	mandatory
	DESCRIPTION
		"Indicates the gaugeIndex which must be used to create the
		next alarm. Index is set to GAUGE_TABLE_FULL (zero) if
		there are no free rows in the table."
	::= { gauges 9 }

--  3Com Alarm Traps
--	These are no longer used. The RMON traps are used in preference.
--	These definitions are provided only for backward compatibility

gaugesThresholdTrap     TRAP-TYPE
        ENTERPRISE      a3Com
        VARIABLES       {
                                gaugeItemId,
                                gaugeThresholdLevel,
                                gaugeSamplePeriod,
                                gaugeSamplesPerAverage
                        }
        DESCRIPTION     "
        		Generated when the Alarm value for this Alarm crosses
                        the Threshold Level."
        ::= 16

gaugesRecoveryTrap      TRAP-TYPE
        ENTERPRISE      a3Com
        VARIABLES       {
                                gaugeItemId,
                                gaugeRecoveryLevel,
                                gaugeSamplePeriod,
                                gaugeSamplesPerAverage
                        }
        DESCRIPTION     "
        		Generated when the Alarm value for this Alarm crosses
                        the Recovery Level."
        ::= 17

-- --------------------------------------------------------------------
-- ************************ RMON ALARM TABLE **************************
-- --------------------------------------------------------------------

          --  Remote Network Monitoring MIB

              rmon    OBJECT IDENTIFIER ::= { mib-2 16 }

              statistics        OBJECT IDENTIFIER ::= { rmon 1 }
              history           OBJECT IDENTIFIER ::= { rmon 2 }
              alarm             OBJECT IDENTIFIER ::= { rmon 3 }
              hosts             OBJECT IDENTIFIER ::= { rmon 4 }
              hostTopN          OBJECT IDENTIFIER ::= { rmon 5 }
              matrix            OBJECT IDENTIFIER ::= { rmon 6 }
              filter            OBJECT IDENTIFIER ::= { rmon 7 }
              capture           OBJECT IDENTIFIER ::= { rmon 8 }
              event             OBJECT IDENTIFIER ::= { rmon 9 }

          alarmTable OBJECT-TYPE
              SYNTAX SEQUENCE OF AlarmEntry
              ACCESS not-accessible
              STATUS mandatory
              DESCRIPTION
                  "A list of alarm entries."
              ::= { alarm 1 }

          alarmEntry OBJECT-TYPE
              SYNTAX AlarmEntry
              ACCESS not-accessible
              STATUS mandatory
              DESCRIPTION
                  "A list of parameters that set up a periodic checking
                  for alarm conditions."
              INDEX { alarmIndex }
              ::= { alarmTable 1 }

          AlarmEntry ::= SEQUENCE {
              alarmIndex                    INTEGER (1..65535),
              alarmInterval                 INTEGER,
              alarmVariable                 OBJECT IDENTIFIER,
              alarmSampleType               INTEGER,
              alarmValue                    INTEGER,
              alarmStartupAlarm             INTEGER,
              alarmRisingThreshold          INTEGER,
              alarmFallingThreshold         INTEGER,
              alarmRisingEventIndex         INTEGER (0..65535),
              alarmFallingEventIndex        INTEGER (0..65535),
              alarmOwner                    DisplayString,
              alarmStatus                   INTEGER
          }

          alarmIndex OBJECT-TYPE
              SYNTAX INTEGER (1..65535)
              ACCESS read-only
              STATUS mandatory
              DESCRIPTION
                  "An index that uniquely identifies an entry in the
                  alarm table.  Each such entry defines a
                  diagnostic sample at a particular interval
                  for an object on the device."
              ::= { alarmEntry 1 }

          alarmInterval OBJECT-TYPE
              SYNTAX INTEGER
              ACCESS read-write
              STATUS mandatory
              DESCRIPTION
                  "The interval in seconds over which the data is
                  sampled and compared with the rising and falling
                  thresholds.  When setting this variable, care
                  should be given to ensure that the variable being
                  monitored will not exceed 2^31 - 1 and roll
                  over the alarmValue object during the interval.

                  This object may not be modified if the associated
                  alarmStatus object is equal to valid(1)."
              ::= { alarmEntry 2 }

          alarmVariable OBJECT-TYPE
              SYNTAX OBJECT IDENTIFIER
              ACCESS read-write
              STATUS mandatory
              DESCRIPTION
                  "The object identifier of the particular variable to
                  be sampled.  Only variables that resolve to an ASN.1
                  primitive type of INTEGER (INTEGER, Counter, Gauge,
                  or TimeTicks) may be sampled.

                  Because SNMP access control is articulated entirely
                  in terms of the contents of MIB views, no access
                  control mechanism exists that can restrict the value of
                  this object to identify only those objects that exist
                  in a particular MIB view.  Because there is thus no
                  acceptable means of restricting the read access that
                  could be obtained through the alarm mechanism, the
                  probe must only grant write access to this object in
                  those views that have read access to all objects on
                  the probe.

                  During a set operation, if the supplied variable
                  name is not available in the selected MIB view, a
                  badValue error must be returned.  If at any time
                  the variable name of an established alarmEntry is
                  no longer available in the selected MIB view, the
                  probe must change the status of this alarmEntry
                  to invalid(4).

                  This object may not be modified if the associated
                  alarmStatus object is equal to valid(1)."
              ::= { alarmEntry 3 }

          alarmSampleType OBJECT-TYPE
              SYNTAX INTEGER {
                  absoluteValue(1),
                  deltaValue(2)
              }
              ACCESS read-write
              STATUS mandatory
              DESCRIPTION
                  "The method of sampling the selected variable and
                  calculating the value to be compared against the
                  thresholds.  If the value of this object is
                  absoluteValue(1), the value of the selected variable
                  will be compared directly with the thresholds at the
                  end of the sampling interval.  If the value of this
                  object is deltaValue(2), the value of the selected
                  variable at the last sample will be subtracted from
                  the current value, and the difference compared with
                  the thresholds.

                  This object may not be modified if the associated
                  alarmStatus object is equal to valid(1)."
              ::= { alarmEntry 4 }

          alarmValue OBJECT-TYPE
              SYNTAX INTEGER
              ACCESS read-only
              STATUS mandatory
              DESCRIPTION
                  "The value of the statistic during the last sampling
                  period.  The value during the current sampling period
                  is not made available until the period is completed."
              ::= { alarmEntry 5 }

          alarmStartupAlarm OBJECT-TYPE
              SYNTAX INTEGER {
                  risingAlarm(1),
                  fallingAlarm(2),
                  risingOrFallingAlarm(3)
              }
              ACCESS read-write
              STATUS mandatory
              DESCRIPTION
                  "The alarm that may be sent when this entry is first
                  set to valid.  If the first sample after this entry
                  becomes valid is greater than or equal to the
                  risingThreshold and alarmStartupAlarm is equal to
                  risingAlarm(1) or risingOrFallingAlarm(3), then a
                  single rising alarm will be generated.  If the first
                  sample after this entry becomes valid is less than
                  or equal to the fallingThreshold and
                  alarmStartupAlarm is equal to fallingAlarm(2) or
                  risingOrFallingAlarm(3), then a single falling
                  alarm will be generated.

                  This object may not be modified if the associated
                  alarmStatus object is equal to valid(1)."
              ::= { alarmEntry 6 }

          alarmRisingThreshold OBJECT-TYPE
              SYNTAX INTEGER
              ACCESS read-write
              STATUS mandatory
              DESCRIPTION
                  "A threshold for the sampled statistic.  When the
                  current sampled value is greater than or equal to
                  this threshold, and the value at the last sampling
                  interval was less than this threshold, a single
                  event will be generated.
                  A single event will also be generated if the first
                  sample after this entry becomes valid is greater
                  than or equal to this threshold and the associated
                  alarmStartupAlarm is equal to risingAlarm(1) or
                  risingOrFallingAlarm(3).

                  After a rising event is generated, another such event
                  will not be generated until the sampled value
                  falls below this threshold and reaches the
                  alarmFallingThreshold.

                  This object may not be modified if the associated
                  alarmStatus object is equal to valid(1)."
              ::= { alarmEntry 7 }

          alarmFallingThreshold OBJECT-TYPE
              SYNTAX INTEGER
              ACCESS read-write
              STATUS mandatory
              DESCRIPTION
                  "A threshold for the sampled statistic.  When the
                  current sampled value is less than or equal to
                  this threshold, and the value at the last sampling
                  interval was greater than this threshold, a single
                  event will be generated.
                  A single event will also be generated if the first
                  sample after this entry becomes valid is less than or
                  equal to this threshold and the associated
                  alarmStartupAlarm is equal to fallingAlarm(2) or
                  risingOrFallingAlarm(3).

                  After a falling event is generated, another such event
                  will not be generated until the sampled value
                  rises above this threshold and reaches the
                  alarmRisingThreshold.

                  This object may not be modified if the associated
                  alarmStatus object is equal to valid(1)."
              ::= { alarmEntry 8 }

          alarmRisingEventIndex OBJECT-TYPE
              SYNTAX INTEGER (0..65535)
              ACCESS read-write
              STATUS mandatory
              DESCRIPTION
                  "The index of the eventEntry that is
                  used when a rising threshold is crossed.  The
                  eventEntry identified by a particular value of
                  this index is the same as identified by the same value
                  of the eventIndex object.  If there is no
                  corresponding entry in the eventTable, then
                  no association exists.  In particular, if this value
                  is zero, no associated event will be generated, as
                  zero is not a valid event index.

                  This object may not be modified if the associated
                  alarmStatus object is equal to valid(1)."
              ::= { alarmEntry 9 }

          alarmFallingEventIndex OBJECT-TYPE
              SYNTAX INTEGER (0..65535)
              ACCESS read-write
              STATUS mandatory
              DESCRIPTION
                  "The index of the eventEntry that is
                  used when a falling threshold is crossed.  The
                  eventEntry identified by a particular value of
                  this index is the same as identified by the same value
                  of the eventIndex object.  If there is no
                  corresponding entry in the eventTable, then
                  no association exists.  In particular, if this value
                  is zero, no associated event will be generated, as
                  zero is not a valid event index.

                  This object may not be modified if the associated
                  alarmStatus object is equal to valid(1)."

              ::= { alarmEntry 10 }

          alarmOwner OBJECT-TYPE
              SYNTAX DisplayString
              ACCESS read-write
              STATUS mandatory
              DESCRIPTION
                  "The entity that configured this entry and is
                  therefore using the resources assigned to it."
              ::= { alarmEntry 11 }

          alarmStatus OBJECT-TYPE
              SYNTAX INTEGER
                         { valid(1),
                           createRequest(2),
                           underCreation(3),
                           invalid(4)
                         }
              ACCESS read-write
              STATUS mandatory
              DESCRIPTION
                  "The status of this alarm entry."
              ::= { alarmEntry 12 }

-- --------------------------------------------------------------------
-- ************************ RMON EVENT TABLE **************************
-- --------------------------------------------------------------------

          --  Remote Network Monitoring MIB

          eventTable OBJECT-TYPE
              SYNTAX SEQUENCE OF EventEntry
              ACCESS not-accessible
              STATUS mandatory
              DESCRIPTION
                  "A list of events to be generated."
              ::= { event 1 }

          eventEntry OBJECT-TYPE
              SYNTAX EventEntry
              ACCESS not-accessible
              STATUS mandatory
              DESCRIPTION
                  "A set of parameters that describe an event to be
                  generated when certain conditions are met."
              INDEX { eventIndex }
              ::= { eventTable 1 }

          EventEntry ::= SEQUENCE {
              eventIndex          INTEGER (1..65535),
              eventDescription    DisplayString (SIZE (0..127)),
              eventType           INTEGER,
              eventCommunity      OCTET STRING (SIZE (0..127)),
              eventLastTimeSent   TimeTicks,
              eventOwner          DisplayString,
              eventStatus         INTEGER
          }

          eventIndex OBJECT-TYPE
              SYNTAX INTEGER (1..65535)
              ACCESS read-only
              STATUS mandatory
              DESCRIPTION
                  "An index that uniquely identifies an entry in the
                  event table.  Each such entry defines one event that
                  is to be generated when the appropriate conditions
                  occur."
              ::= { eventEntry 1 }

          eventDescription OBJECT-TYPE
              SYNTAX DisplayString (SIZE (0..127))
              ACCESS read-write
              STATUS mandatory
              DESCRIPTION
                  "A comment describing this event entry."
              ::= { eventEntry 2 }

          eventType OBJECT-TYPE
              SYNTAX INTEGER {
                      none(1),
                      log(2),
                      snmp-trap(3),    -- send an SNMP trap
                      log-and-trap(4)
              }
              ACCESS read-write
              STATUS mandatory
              DESCRIPTION
                  "The type of notification that the probe will make
                  about this event.  In the case of log, an entry is
                  made in the log table for each event.  In the case of
                  snmp-trap, an SNMP trap is sent to one or more
                  management stations."
              ::= { eventEntry 3 }

          eventCommunity OBJECT-TYPE
              SYNTAX OCTET STRING (SIZE (0..127))
              ACCESS read-write
              STATUS mandatory
              DESCRIPTION
                  "If an SNMP trap is to be sent, it will be sent to
                  the SNMP community specified by this octet string.
                  In the future this table will be extended to include
                  the party security mechanism.  This object shall be
                  set to a string of length zero if it is intended that
                  that mechanism be used to specify the destination of
                  the trap."
              ::= { eventEntry 4 }

          eventLastTimeSent OBJECT-TYPE
              SYNTAX TimeTicks
              ACCESS read-only
              STATUS mandatory
              DESCRIPTION
                  "The value of sysUpTime at the time this event
                  entry last generated an event.  If this entry has
                  not generated any events, this value will be
                  zero."
              ::= { eventEntry 5 }

          eventOwner OBJECT-TYPE
              SYNTAX DisplayString
              ACCESS read-write
              STATUS mandatory
              DESCRIPTION
                  "The entity that configured this entry and is therefore
                  using the resources assigned to it.

                  If this object contains a string starting with 'monitor'
                  and has associated entries in the log table, all
                  connected management stations should retrieve those
                  log entries, as they may have significance to all
                  management stations connected to this device"
              ::= { eventEntry 6 }

          eventStatus OBJECT-TYPE
              SYNTAX INTEGER
                         { valid(1),
                           createRequest(2),
                           underCreation(3),
                           invalid(4)
                         }
              ACCESS read-write
              STATUS mandatory
              DESCRIPTION
                  "The status of this event entry.

                  If this object is not equal to valid(1), all associated
                  log entries shall be deleted by the agent."
              ::= { eventEntry 7 }

          logTable OBJECT-TYPE
              SYNTAX SEQUENCE OF LogEntry
              ACCESS not-accessible
              STATUS mandatory
              DESCRIPTION
                  "A list of events that have been logged."
              ::= { event 2 }

          logEntry OBJECT-TYPE
              SYNTAX LogEntry
              ACCESS not-accessible
              STATUS mandatory
              DESCRIPTION
                  "A set of data describing an event that has been
                  logged."
              INDEX { logEventIndex, logIndex }
              ::= { logTable 1 }

          LogEntry ::= SEQUENCE {
              logEventIndex           INTEGER (1..65535),
              logIndex                INTEGER,
              logTime                 TimeTicks,
              logDescription          DisplayString (SIZE (0..255))
          }

          logEventIndex OBJECT-TYPE
              SYNTAX INTEGER (1..65535)
              ACCESS read-only
              STATUS mandatory
              DESCRIPTION
                  "The event entry that generated this log
                  entry.  The log identified by a particular
                  value of this index is associated with the same
                  eventEntry as identified by the same value
                  of eventIndex."
              ::= { logEntry 1 }

          logIndex OBJECT-TYPE
              SYNTAX INTEGER
              ACCESS read-only
              STATUS mandatory
              DESCRIPTION
                  "An index that uniquely identifies an entry
                  in the log table amongst those generated by the
                  same eventEntries.  These indexes are
                  assigned beginning with 1 and increase by one
                  with each new log entry.  The association
                  between values of logIndex and logEntries
                  is fixed for the lifetime of each logEntry.
                  The agent may choose to delete the oldest
                  instances of logEntry as required because of
                  lack of memory.  It is an implementation-specific
                  matter as to when this deletion may occur."
              ::= { logEntry 2 }

          logTime OBJECT-TYPE
              SYNTAX TimeTicks
              ACCESS read-only
              STATUS mandatory
              DESCRIPTION
                  "The value of sysUpTime when this log entry was
                  created."
              ::= { logEntry 3 }

          logDescription OBJECT-TYPE
              SYNTAX DisplayString (SIZE (0..255))
              ACCESS read-only
              STATUS mandatory
              DESCRIPTION
                  "An implementation dependent description of the
                  event that activated this log entry."
              ::= { logEntry 4 }

          --  Remote Network Monitoring Traps

          risingAlarm TRAP-TYPE
              ENTERPRISE rmon
              VARIABLES { alarmIndex, alarmVariable, alarmSampleType,
                          alarmValue, alarmRisingThreshold }
              DESCRIPTION
                  "The SNMP trap that is generated when an alarm
                  entry crosses its rising threshold and generates
                  an event that is configured for sending SNMP
                  traps."
              ::= 1

          fallingAlarm TRAP-TYPE
              ENTERPRISE rmon
              VARIABLES { alarmIndex, alarmVariable, alarmSampleType,
                          alarmValue, alarmFallingThreshold }
              DESCRIPTION
                  "The SNMP trap that is generated when an alarm
                  entry crosses its falling threshold and generates
                  an event that is configured for sending SNMP
                  traps."
              ::= 2
-- --------------------------------------------------------------------
-- **************************** ASCII AGENT GROUP *********************
-- --------------------------------------------------------------------

        -- Implementation of the ASCII Agent group is mandatory for all
        -- systems.

ascTimeAttemptedLogin OBJECT-TYPE
        SYNTAX  TimeTicks
        ACCESS	read-write
	STATUS	mandatory
	DESCRIPTION
		"Time in hundredths of a second when the last
		 Login was attempted. Note, that only the ASCII Agent can
		 write to this parameter. A write operation from any other
		 agent will result in an ERROR"
	::= { asciiAgent 1 }

ascUserNameForLastAttemptedLogin OBJECT-TYPE
        SYNTAX  DisplayString (SIZE (0..10))
        ACCESS	read-write
	STATUS	mandatory
	DESCRIPTION
		"An ASCII string used when attempted login. Empty string
		 is NOT valid. Note, that only the ASCII Agent can
		 write to this parameter. A write operation from any other
		 agent will result in an ERROR"
	::= { asciiAgent 2 }

ascLoginStatus OBJECT-TYPE
        SYNTAX  INTEGER {
        			loginOKFromTelnet (1),
        			loginOKFromSerialPort (2),
        			deniedAccessFromTelnet (3),
        			deniedAccessFromSerialPort (4),
        			unknownUserFromTelnet (5),
        			unknownUserFromSerialPort (6),
        			incorrectPasswordFromTelnet (7),
        			incorrectPasswordFromSerialPort (8),
        			securityViolationFromTelnet (9),
        			securityViolationFromSerialPort (10),
				nologin (11)
        		}
        ACCESS	read-write
	STATUS	mandatory
	DESCRIPTION
		"Status of last attempted login. The value 'loginOKFromTelnet'
		or 'loginOKFromSerialPort' is used to show that the user was
		allowed access via Telnet or Serial Port.
		'DeniedAccessFromTelnet' indicates that a user was denied
		access via Telnet. The value 'unknownUserFromTelnet' is used
		to show that a user attempted to login with an invalid user
		name from a Telnet session and 'incorrectPasswordFromTelnet'
		is used to show that an invalid password was entered having
		supplied a valid user name. The value
		'securityViolationFromTelnet' is used to indicate that a user
		has entered the password incorrectly three time consecutively
		from a Telnet session. Note that only the ASCII Agent can
		write to this parameter. A write operation from any other
		agent will result in an ERROR"
	::= { asciiAgent 3 }

ascLocalManagementBanner OBJECT-TYPE
        SYNTAX  DisplayString (SIZE (0..490))
        ACCESS	read-write
	STATUS	mandatory
	DESCRIPTION
		"An ASCII string describing the Banner to appear on the
		 FIRST screen of the Local Management Terminal.
		 The string of 490 characters defines a region in the
		 centre of the screen which is 7 Rows by 70 Columns"
	::= { asciiAgent 4 }

-- --------------------------------------------------------------------
-- ASCII Agent Traps
-- --------------------------------------------------------------------
localManagementUpdate TRAP-TYPE
              ENTERPRISE  a3Com
              DESCRIPTION
                          "A local management update trap indicates that
                          the configuration of the device has been modified
                          via the ascii agent. This may be through Telnet or
                          the V24 port."
              ::= 14

securityViolation TRAP-TYPE
              ENTERPRISE  a3Com
              VARIABLES   {ascUserNameForLastAttemptedLogin,ascLoginStatus }
              DESCRIPTION
                          "A security violation trap indicates that a user has
                          attempted to login and failed to enter the correct password
                          Three times consecutively."
              ::= 15

-- --------------------------------------------------------------------
--			END OF ASCII AGENT GROUP
-- --------------------------------------------------------------------
-- --------------------------------------------------------------------
-- ********************* SERIAL INTERFACE GROUP ********************
-- --------------------------------------------------------------------

          -- the Serial Interface Module

siSlipPort OBJECT-TYPE
	SYNTAX  INTEGER
	ACCESS  read-write
	STATUS  mandatory
	DESCRIPTION
		"This object identifies the serial port which
		SLIP can use to send/receive packets. If this
		object is set to 0xFFFF, then SLIP cannot send/receive
		packets."

	::= { serialIf 1 }

--
--	LinkBuilder FMS Config V.24 Table
--

configV24Table	OBJECT-TYPE
	SYNTAX	SEQUENCE OF ConfigV24Entry
	ACCESS	not-accessible
	STATUS	mandatory
	DESCRIPTION
		"Configuration parameters for all the V.24 ports in a system."
	::= {serialIf 2}

configV24Entry	OBJECT-TYPE
	SYNTAX	ConfigV24Entry
	ACCESS	not-accessible
	STATUS	mandatory
	DESCRIPTION
		"Configuration parameters for a V.24 port in the system."
	INDEX	{configV24PortID}
	::= {configV24Table 1}

	ConfigV24Entry ::= SEQUENCE {
		configV24PortID		INTEGER,
		configV24ConnType	INTEGER,
		configV24AutoConfig	INTEGER,
		configV24Speed		INTEGER,
		configV24CharSize	INTEGER,
		configV24StopBits	INTEGER,
		configV24Parity		INTEGER,
		configV24DSRControl	INTEGER,
		configV24DCDControl	INTEGER,
		configV24FlowControl	INTEGER,
		configV24Update		INTEGER
	}

configV24PortID	OBJECT-TYPE
	SYNTAX	INTEGER (1..16)
	ACCESS	read-only
	STATUS	mandatory
	DESCRIPTION
		"This attribute uniquely identifies this V.24 port, it is
		the index for the V.24 table."
	::= {configV24Entry 1}

configV24ConnType	OBJECT-TYPE
	SYNTAX	INTEGER {
		local	(1),
		remote	(2)
		}
	ACCESS	read-write
	STATUS	mandatory
	DESCRIPTION
		"This determines if the V.24 port is to be connected locally
		to a terminal or terminal emulator in which case no interface
		signals need to be asserted unless requested by other
		management options below or if the V.24 port is to be
		connected to a modem when at least DSR is required to be
		asserted."
	::= {configV24Entry 2}

configV24AutoConfig	OBJECT-TYPE
	SYNTAX	INTEGER {
		disabled	(1),
		enabled		(2)
		}
	ACCESS	read-write
	STATUS	mandatory
	DESCRIPTION
		"This determines if the configuration parameters for the
		V.24 port, speed, parity, stop bits, character size, are to
		be determined automatically from an initial character sequence
		entered by the user or they will be defined by the management
		options below."
	::= {configV24Entry 3}

configV24Speed	OBJECT-TYPE
	SYNTAX	INTEGER {
		speed1200	(4),
		speed2400	(5),
		speed4800	(6),
		speed9600	(7),
		speed19200	(8),
		speed38400	(9)
		}
	ACCESS	read-write
	STATUS	mandatory
	DESCRIPTION
		"This determines the receive and transmit speed of the V.24
		port unless the autoconfigure attribute is enabled when the
		data rates are determined from the line. Split rx and tx
		speeds are not possible."
	::= {configV24Entry 4}

configV24CharSize	OBJECT-TYPE
	SYNTAX	INTEGER {
		size7	(3),
		size8	(4)
		}
	ACCESS	read-write
	STATUS	mandatory
	DESCRIPTION
		"This determines the character size, unless the autoconfigure
		attribute is enabled when character size is determined
		automatically from the line, it may be set to either 7
		or 8 bits."
	::= {configV24Entry 5}

configV24StopBits	OBJECT-TYPE
	SYNTAX	INTEGER {
		stopOne		(1),
		stopOneDotFive	(2),
		stopTwo		(3)
		}
	ACCESS	read-write
	STATUS	mandatory
	DESCRIPTION
		"This determines the number of stop bits."
	::= {configV24Entry 6}

configV24Parity	OBJECT-TYPE
	SYNTAX	INTEGER {
		noParity	(1),
		spaceParity	(2),
		markParity	(3),
		oddParity	(4),
		evenParity	(5)
		}
	ACCESS	read-write
	STATUS	mandatory
	DESCRIPTION
		"This determines the parity option to be used, unless the
		autoconfigure attribute is enabled when parity is determined
		automatically from the line, it may be set to either no
		parity, space (parity bit always 0), mark (parity bit always
		1), odd or even."
	::= {configV24Entry 7}

configV24DSRControl	OBJECT-TYPE
	SYNTAX	INTEGER {
		disabled	(1),
		enabled		(2)
		}
	ACCESS	read-write
	STATUS	mandatory
	DESCRIPTION
		"This attribute is only applicable to local connection types.
		It determines if DSR need be asserted for a local connection
		to be made and if the connection need be released if DSR is
		seen deasserted."
	::= {configV24Entry 8}

configV24DCDControl	OBJECT-TYPE
	SYNTAX	INTEGER {
		disabled	(1),
		enabled		(2)
		}
	ACCESS	read-write
	STATUS	mandatory
	DESCRIPTION
		"This attribute is only applicable to local connection types.
		It determines if DCD need be asserted for a local connection
		to be made and if the connection should be release if DCD is
		seen deasserted."
	::= {configV24Entry 9}

configV24FlowControl	OBJECT-TYPE
	SYNTAX	INTEGER {
		noFlowControl		(1),
		xonXoff			(2),
		rtsCtsFullDplx		(3),
		rtsCtsHalfDplx		(4)
		}
	ACCESS	read-write
	STATUS	mandatory
	DESCRIPTION
		"This determines the flow control protocol to be used, either
		no flow control, xon-xoff, rts-cts full duplex or rts-cts.
		Full duplex rts/cts uses the rts and cts lines as two
		independent signals. The DTE signals to the DCE that it is
		prepared to accept more data by asserting RTS, the DCE signals
		to the DTE that is is prepared to accept more data by
		asserting CTS. Half duplex rts/cts (the conventional way) uses
		CTS as a response to RTS, the DCE flow controls the DTE by
		only returning CTS is response to a RTS from the DTE when the
		DCE can accept more data. The DTE can flow control the DCE by
		raising RTS when it does not want to receive any more input
		and dropping it when it is ready to receive more."
	::= {configV24Entry 10}

configV24Update	OBJECT-TYPE
	SYNTAX	INTEGER {
		nochange	(1),
		update		(2)
		}
	ACCESS	read-write
	STATUS	mandatory
	DESCRIPTION
		"This attribute may be written to to force the operational
		V.24 port parameters to be updated."
	::= {configV24Entry 11}


-- ***************************************************************************
--
-- Connect 3 End Station Table
--
-- Database State
--
-- ***************************************************************************
esDatabaseState OBJECT-TYPE
       SYNTAX INTEGER { noChange(1), modified(2) }
       ACCESS   read-write
       STATUS   mandatory
       DESCRIPTION "
This parameter is normally set to
'NO-CHANGE'. When any change is made to the database the value of this
parameter becomes 'MODIFIED'. It will remain in this state until a
manager sets it back to NO-CHANGE.
        "
	::= { endStation 1 }

-- ***************************************************************************
--
-- Flush Table
--
-- ***************************************************************************
esDatabaseFlush OBJECT-TYPE
       SYNTAX   INTEGER {  flush (1) }
       ACCESS   write-only
       STATUS   mandatory
       DESCRIPTION "
This parameter clears the End Station Database"
	::= { endStation 2 }

-- ***************************************************************************
--
-- End Station Table
--
-- Note that the end station database is global and applies across all
-- repeaters in the chassis. There is no distinction between units on
-- one repeater and those on another. Given a unit number the manager
-- can read the configuration values to determine the actual repeater
-- association at that moment.
-- ***************************************************************************
esTable OBJECT-TYPE
	SYNTAX 		SEQUENCE OF EsTableEntry
	ACCESS		not-accessible
	STATUS		mandatory
	DESCRIPTION     "End Station Table"
	::= { endStation 3 }

esTableEntry OBJECT-TYPE
	SYNTAX		EsTableEntry
	ACCESS		not-accessible
	STATUS		mandatory
	DESCRIPTION "
The end station database maintains information concerning end-station
address information against device port for 802.3 repeater type
devices. This table provides one of three views on that database.

The view provided by this particular table is indexed firstly on
address type and then on address and so can be used to read the entire
contents of the database in end-station address order. Additionally
one can read all addresses of a certain type from the database, e.g.
all IP addresses known.

There are some points to note when reading the contents of the end
station table. Firstly the repeater number reported will change if a
unit is moved from one repeater within a device to another or if a
unit is isolated. Secondly an address will only appear in the table
once. If an address which is already present in the database is found
on another port then the original record is changed and the 'modified'
flag set for that entry."
	INDEX		{ esAddrType, esAddress }
	::= { esTable 1 }

	EsTableEntry ::= SEQUENCE {
		esAddrType		INTEGER,
		esAddress		OCTET STRING,
		esSlotNumber		INTEGER,
		esPortNumber		INTEGER
	}

esAddrType OBJECT-TYPE
	SYNTAX INTEGER { ieee8021(1),internet(2),ipx(3) }
	ACCESS		read-only
	STATUS		mandatory
	DESCRIPTION	"
The end station database is capable of storing information for a
number of different protocols. Each protocol has it's own addressing
format. This parameter allows access to the end station database
indexed on address type. For example to read all IEE8021 addresses
simply start with a get-next operation on IEEE8021.0 and read until
the type changes."
	::= { esTableEntry 1 }

esAddress OBJECT-TYPE
	SYNTAX		OCTET STRING	(SIZE(6))
	ACCESS		read-only
	STATUS		mandatory
	DESCRIPTION	"
The address information held in this entry of the database. The length and
format of the string depends on the address type. For example a MAC address
will be a 6 byte OCTET STRING, an IP address a 4 byte OCTET STRING."
	::= { esTableEntry 2 }

esSlotNumber OBJECT-TYPE
	SYNTAX		INTEGER
	ACCESS		read-only
	STATUS		mandatory
	DESCRIPTION	"
Number of unit on which this address was learnt."
	::= { esTableEntry 3 }

esPortNumber OBJECT-TYPE
	SYNTAX		INTEGER
	ACCESS		read-only
	STATUS		mandatory
	DESCRIPTION	"
Port number of unit on which this address was learnt."
	::= { esTableEntry 4 }

-- ***************************************************************************
-- esModTable
-- This table provides a filtered view of the end station database.  The
-- means of access are the same, i.e. addressType.address, but only entries
-- in the database that have the modified flag set to MODIFIED will
-- appear in the view of the table presented by this table.
-- ***************************************************************************
esModTable OBJECT-TYPE
	SYNTAX 		SEQUENCE OF EsModTableEntry
	ACCESS		not-accessible
	STATUS		mandatory
	DESCRIPTION     "End Station Table ( Modified )"
	::= { endStation 4 }

esModTableEntry OBJECT-TYPE
	SYNTAX		EsModTableEntry
	ACCESS		not-accessible
	STATUS		mandatory
	DESCRIPTION "
The end station database maintains information concerning end-station
address information against device port for 802.3 repeater type
devices. This table provides one of three views on that database.

The view provided by this particular table is indexed firstly on
address type and then on address. The view is restricted to include
only those entries in the database which have the MODIFIED flag set, i.e.
that have been changed since the database was last viewed by the
manager. This table can be used to read all the modified entries in the
table. This is the table generally used to update the contents of a
station map in a management station. Note that it can take a
reasonable time to read the contents of the table and in that time
other changes may occur. To detect this an additional MIB parameter is
specified 'esDatabaseState'. This parameter is normally set to
'NO-CHANGE'. When any change is made to the database the value of this
parameter becomes 'MODIFIED'. It will remain in this state until a
manager sets it back to NO-CHANGE. The recommended access for this
table is as follows:

	do {
		write 'NO-CHANGE' to esDatabaseState
		read modified table
		read esDatabaseState
	} while esDatabaseState is MODIFIED

There are some points to note when reading the contents of the end
station table. Firstly the repeater number reported will change if a
unit is moved from one repeater within a device to another or if a
unit is isolated. Secondly an address will only appear in the table
once. If an address which is already present in the database is found
on another port then the original record is changed and the 'modified'
flag set for that entry."
	INDEX		{ esModAddrType, esModAddress }
	::= { esModTable 1 }

	EsModTableEntry ::= SEQUENCE {
		esModAddrType		INTEGER,
		esModAddress		OCTET STRING,
		esModSlotNumber		INTEGER,
		esModPortNumber		INTEGER
	}

esModAddrType OBJECT-TYPE
	SYNTAX	INTEGER {ieee8021(1), internet(2), ipx(3) }
	ACCESS		read-only
	STATUS		mandatory
	DESCRIPTION	"
The end station database is capable of storing information for a
number of different protocols. Each protocol has it's own addressing
format. This parameter allows access to the end station database
indexed on address type. For example to read all IEE8021 addresses
simply start with a get-next operation on IEEE8021.0 and read until
the type changes."
	::= { esModTableEntry 1 }

esModAddress OBJECT-TYPE
	SYNTAX		OCTET STRING	(SIZE(6))
	ACCESS		read-only
	STATUS		mandatory
	DESCRIPTION	"
The address information held in this entry of the database. The length and
format of the string depends on the address type. For example a MAC address
will be a 6 byte OCTET STRING, an IP address a 4 byte OCTET STRING."
	::= { esModTableEntry 2 }

esModSlotNumber OBJECT-TYPE
	SYNTAX		INTEGER
	ACCESS		read-only
	STATUS		mandatory
	DESCRIPTION	"
Unit number on which this address was learnt."
	::= { esModTableEntry 3 }

esModPortNumber OBJECT-TYPE
	SYNTAX		INTEGER
	ACCESS		read-only
	STATUS		mandatory
	DESCRIPTION	"
Port number of unit on which this address was learnt."
	::= { esModTableEntry 4 }

-- ***************************************************************************
-- esPortAccessTable
-- This table provides a filtered view of the end station database.  The
-- means of access are the same, i.e. addressType.address, but only entries
-- in the database that have the modified flag set to MODIFIED will
-- appear in the view of the table presented by this table.
-- ***************************************************************************
esPortAccessTable OBJECT-TYPE
	SYNTAX 		SEQUENCE OF EsPortAccessEntry
	ACCESS		not-accessible
	STATUS		mandatory
	DESCRIPTION     "End Station Table ( Port Access )"
	::= { endStation 5 }

esPortAccessEntry OBJECT-TYPE
	SYNTAX		EsPortAccessEntry
	ACCESS		not-accessible
	STATUS		mandatory
	DESCRIPTION "
The end station database maintains information concerning end-station
address information against device port for 802.3 repeater type
devices. This table provides one of three views on that database.

The view provided by this particular table allows one to determine the
addresses learnt against a particular port."
	INDEX		{
				ecPortCardNo,
				ecPortPortNo,
				ecPortIndex
			}
	::= { esPortAccessTable 1 }

	EsPortAccessEntry ::= SEQUENCE {
		ecPortCardNo		INTEGER,
		ecPortPortNo		INTEGER,
		ecPortIndex		INTEGER,
		ecPortAddrType		INTEGER,
		ecPortAddress		OCTET STRING
	}

ecPortCardNo OBJECT-TYPE
	SYNTAX		INTEGER
	ACCESS		read-only
	STATUS		mandatory
	DESCRIPTION	"Unit part of the identifier for this port."
	::= { esPortAccessEntry 2 }

ecPortPortNo OBJECT-TYPE
	SYNTAX		INTEGER
	ACCESS		read-only
	STATUS		mandatory
	DESCRIPTION	"
Port number on unit of port for which end station information is required."
	::= { esPortAccessEntry 3 }

ecPortIndex OBJECT-TYPE
	SYNTAX		INTEGER
	ACCESS		read-only
	STATUS		mandatory
	DESCRIPTION	"
Each port may have a number of addresses against it. This index allows
these various addresses to be distinguished. The only stipulation on
this number is that it will be unique for the any combination of unit
and port. The numbers will be returned in numerically ascending order
for a particular unit.port combination but will not be contiguous. For
example the following sequence could be seen:

	Unit		Port		Index
	1		1		211
	1		1		231
	1		1		438
	1		1		672
	1		2		120
etc"
	::= { esPortAccessEntry 4 }

ecPortAddrType OBJECT-TYPE
	SYNTAX INTEGER { ieee8021(1),internet(2),ipx(3) }
	ACCESS		read-only
	STATUS		mandatory
	DESCRIPTION	"
The end station database is capable of storing information for a
number of different protocols. Each protocol has it's own addressing
format. This parameter identifies the type of address in this entry of
the table."
	::= { esPortAccessEntry 5 }

ecPortAddress OBJECT-TYPE
	SYNTAX		OCTET STRING	(SIZE(6))
	ACCESS		read-only
	STATUS		mandatory
	DESCRIPTION	"
The address information held in this entry of the database. The length and
format of the string depends on the address type. For example a MAC address
will be a 6 byte OCTET STRING, an IP address a 4 byte OCTET STRING."
	::= { esPortAccessEntry 6 }

-- **********************************************************************
-- Trap definitions for the end station database.
-- **********************************************************************
estStateChange TRAP-TYPE
	ENTERPRISE a3Com
 	DESCRIPTION "
When the end-station table moves from the noChange to modified state this
trap is generated. The trap is sent once on this transition and not
subsequently until the 'Database State' is changed back to 'noChange' by a
manager."
 	::= 19

estTableFull TRAP-TYPE
	ENTERPRISE a3Com
 	DESCRIPTION "
When the end-station table becomes full this trap is generated."
 	::= 20
-- -----------------------------------------------------------------------------
--		 REMOTE POLL TABLE
-- -----------------------------------------------------------------------------

pollTable	OBJECT-TYPE
	SYNTAX	SEQUENCE OF PollTableEntry
	ACCESS	not-accessible
	STATUS	mandatory
	DESCRIPTION
	"This table is used to provide remote device monitoring facilities.

	This table allows a list of network devices to be set up
	and polled regularly (or only once) by a variety of protocols.
	The table can be configured to inform the management station(s)
	of devices that are not responding to polls or that have started
	to respond after a period of silence.

	The minimum effort required to do a single poll is
	1. In one packet, Write the address, rate=once-only(1) and
	   RowStatus=CreateAndGo.
	2. In the next packet, read the roundTripTime.

	The minimum effort required to monitor a device is
	1. In one packet, Write the address, rate=every-30-seconds(1) and
	   RowStatus=CreateAndGo.
	2. Wait for traps to come in."
	::= { poll 1 }

pollTableEntry	OBJECT-TYPE
	SYNTAX	PollTableEntry
	ACCESS	not-accessible
	STATUS	mandatory
	DESCRIPTION	"A table used to define device monitoring."
	INDEX	{ pollIndex }
	::= { pollTable 1 }

	PollTableEntry ::= SEQUENCE {
		pollIndex		INTEGER,
		pollAddress		DisplayString,
		pollProtocol		INTEGER,
		pollRate		INTEGER,
		pollTargetType		INTEGER,
		pollLastPollSent	TimeTicks,
		pollRoundTripTime	INTEGER,
		pollInformation	DisplayString,
		pollAlarmIndex	INTEGER,
		pollOwner		DisplayString,
		pollRowStatus		INTEGER
	}

pollIndex	OBJECT-TYPE
	SYNTAX	INTEGER (1..255)
	ACCESS	read-only
	STATUS	mandatory
	DESCRIPTION
		"Unique identifier of a row in the Poll Table.

		The actual number of rows that can be created on any particular
		device depends on the memory and processing resources available
		at the time."
	::= { pollTableEntry 1 }

pollAddress	OBJECT-TYPE
	SYNTAX	DisplayString (SIZE(0..50))
	ACCESS	read-write
	STATUS	mandatory
	DESCRIPTION
		"This DisplayString is the network address of the device to
		monitor. Typically this is an IP, MAC or IPX address. The
		following formats can be used.
		IP	nnn.nnn.nnn.nnn	- dotted format
		IPX	AABBCCDD:AABBCCDDEEFF - network : node"
	::= { pollTableEntry 2 }

pollProtocol	OBJECT-TYPE
	SYNTAX	INTEGER	{
			unknown (1),
			ip (2),
			ipx (3),
			learn(4),
			llc(5)
			}
	ACCESS	read-write
	STATUS	mandatory
	DESCRIPTION
		"This defines the protocol to use with which to monitor the device.

		Writing an address to the pollAddress field causes a default
		pollProtocol value to be setup. The default value is derived
		from the format of the address - four bytes means ip(2),
		and 10 bytes means ipx(3) addresses.

		If the requested protocol is not supported or is not compatible
		with the pollAddress, then an error is returned when an attempt
		is made to set the RowStatus to active or notInService."
	DEFVAL	{ unknown }
	::= { pollTableEntry 3 }

pollRate	OBJECT-TYPE
	SYNTAX	INTEGER	{
			once-only (1),
			every-30-seconds (2),
			every-minute (3),
			every-5-minutes (4),
			every-30-minutes (5),
			every-hour (6)
			}
	ACCESS	read-write
	STATUS	mandatory
	DESCRIPTION
		"This defines how often a poll packet is sent to the device.

		If once-only(1) is chosen, then when the RowStatus is set to
		active, a single poll packet is to be sent. There are no
		re-transmissions and no traps are generated. The results of the
		operation can be read in the pollLastPollSent and
		pollRoundTripTime fields. When a reply to the poll is received,
		then the RowStatus is changed to notInService.

		For the other values, setting the RowStatus to active causes the
		device to be regularly polled. The operation of the poll can be
		monitored by reading the pollLastPollSent and pollRoundTripTime
		fields. After four un-successful polls a pollLostContact trap
		is generated. The next successful poll to the device causes a
		pollEstablishedContact trap to be generated. Changing RowStatus
		from the active state causes polling to stop - in particular
		changing RowStatus from active to notInService (and vice-versa)
		is a convenient way of stopping and starting the polls.

		A poll is said to have been un-successful, if no reply has been
		received by the time the device is due to be polled again -
		i.e. if the pollRoundTripTime is still zero.

		By convention, row 1 of the PollTable is only ever used for
		once-only(1) polls.

		The facilities of the RMON Alarm and RMON Event groups are used
		when regular polling is taking place. These groups perform
		the timing, threshold checking and trap generation."
	DEFVAL	{ once-only }
	::= { pollTableEntry 4 }

pollTargetType	OBJECT-TYPE
	SYNTAX	INTEGER	{
			other (1),
			file-server (2)
			}
	ACCESS	read-write
	STATUS	mandatory
	DESCRIPTION
		"This field is provided solely for the purpose of the Network
		Management station to allow extra information to be stored about
		this poll table entry. This value is not used by the device."
	DEFVAL	{ other }
	::= { pollTableEntry 5 }

pollLastPollSent	OBJECT-TYPE
	SYNTAX	TimeTicks
	ACCESS	read-only
	STATUS	mandatory
	DESCRIPTION
		"Reading this variable returns the sysUpTime at which
		the last poll was sent to the device. A value of 0 means
		that no polls have been sent or that the poll could not
		be sent e.g. protocol error."
	DEFVAL	{ 0 }
	::= { pollTableEntry 6 }

pollRoundTripTime	OBJECT-TYPE
	SYNTAX	INTEGER
	ACCESS	read-only
	STATUS	mandatory
	DESCRIPTION
		"This is the round trip time in milli-seconds of the
		most recent poll to the pollAddress device. A value of 0 means
		that no reply has been received from the last poll. Round trip
		times of less than one hundred of a second are reported with the
		value of 10 milli-seconds."
	DEFVAL	{ 0 }
	::= { pollTableEntry 7 }

pollInformation	OBJECT-TYPE
	SYNTAX	DisplayString (SIZE(0..500))
	ACCESS	read-only
	STATUS	mandatory
	DESCRIPTION
		"After each successful poll, this field is updated with some
		protocol specific information that was gleaned from the packet
		exchange.
		For the IPX protocol, this string contains the number of router hops
		made by the poll response packet. For the IP protocol, this string contains
		the value of Time-To-Live from the IP packet header."
	::= { pollTableEntry 8 }

pollAlarmIndex	OBJECT-TYPE
	SYNTAX	INTEGER
	ACCESS	read-only
	STATUS	mandatory
	DESCRIPTION
		"This is a value of alarmIndex from the RMON Alarm Table. The alarm
		indicated is being used by the PollTable to provide the timing and
		trap generation facilities. If this value is 0, then no alarm is
		associated with this PollTable entry."
	DEFVAL	{ 0 }
	::= { pollTableEntry 9 }

pollOwner OBJECT-TYPE
        SYNTAX DisplayString
        ACCESS read-write
        STATUS mandatory
        DESCRIPTION
                  "The RMON OwnerString conventions are used here to
		  help control the multi-manager situations.

              This data type is used to model an administratively
              assigned name of the owner of a resource. This
              information is taken from the NVT ASCII character set.
              It is suggested that this name contain one or more
              of the following:
              IP address, management station name, network manager's
              name, location, or phone number.
              In some cases the agent itself will be the owner of
              an entry.  In these cases, this string shall be set
              to a string starting with 'monitor'.

              SNMP access control is articulated entirely in terms of
              the contents of MIB views; access to a particular SNMP
              object instance depends only upon its presence or
              absence in a particular MIB view and never upon its
              value or the value of related object instances. Thus,
              objects of this type afford resolution of resource
              contention only among cooperating managers; they
              realize no access control function with respect
              to uncooperative parties."
        ::= { pollTableEntry 10 }

pollRowStatus	OBJECT-TYPE
     SYNTAX       INTEGER {
                               -- the following two values are states:
                               -- these values may be read or written
                               active(1),
                               notInService(2),

                               -- the following value is a state:
                               -- this value may be read, but not written
                               notReady(3),

                               -- the following three values are
                               -- actions: these values may be written,
                               --   but are never read
                               createAndGo(4),
                               createAndWait(5),
                               destroy(6)
                           }
	ACCESS	read-write
	STATUS	mandatory
	DESCRIPTION
		"The SNMPv2 RowStatus convention.

		Notes:

		1) Writing any data to a destroyed row, changes its state
		to notReady.
		2) If the status is active or notInService and any of the
		configuration parameters are changed, then the polling stops and
		the status is set to notReady."
	::= { pollTableEntry 11 }

pollNextFreeIndex	OBJECT-TYPE
	SYNTAX	INTEGER (0..255)
	ACCESS	read-only
	STATUS	mandatory
	DESCRIPTION
		"Indicates the the next value of pollIndex which can be used
		to create the next poll entry. This value is set to zero if
		there are no free rows in the table."
	::= { poll 2 }

pollTableSuccessTrap     TRAP-TYPE
        ENTERPRISE      a3Com
        VARIABLES       {
                                pollAddress,
				pollProtocol,
				pollTargetType
                        }
        DESCRIPTION     "This trap is generated when the PollTable in the
			managed agent receives a reply to a poll after a
			sequence of four or more un-successful polls."
        ::= 61

pollTableFailedTrap     TRAP-TYPE
        ENTERPRISE      a3Com
        VARIABLES       {
                                pollAddress,
				pollProtocol,
				pollTargetType
                        }
        DESCRIPTION     "This trap is generated when the PollTable in the
			managed agent fails to receive a reply to four
			successive polls."
        ::= 62

-- --------------------------------------------------------------------
-- ******************** SNMP TRAP TABLES ******************************
-- --------------------------------------------------------------------

	-- snmp Trap Table Database. Tells us where to send SNMP traps to.
	-- Various transport protocols can be setup in the same table.

	-- The original 'trapTable' has been deprecated and has been
	-- replaced by 'snmpTrapTable'. The 'trapTable' is still working
	-- for backward compatibility, but all new applications should
	-- use the new 'snmpTrapTable'

trapTable OBJECT-TYPE
	SYNTAX SEQUENCE OF TrapEntry
	ACCESS not-accessible
	STATUS deprecated
	DESCRIPTION
		"The snmp Trap database "
	::= {localSnmp 1}

trapEntry OBJECT-TYPE
	SYNTAX TrapEntry
	ACCESS not-accessible
	STATUS deprecated
	DESCRIPTION
		"A single  snmp Trap entry"
	INDEX	{ trapDestination }
	::= { trapTable 1}

TrapEntry ::= SEQUENCE {
        trapStatus
                INTEGER,
	trapDestination
		IpAddress,
	trapCommunity
		DisplayString,
	trapSubject
		OBJECT IDENTIFIER,
	trapCategory
		INTEGER,
	trapThrottle
		INTEGER
}

trapStatus OBJECT-TYPE
	SYNTAX	INTEGER { valid(1), invalid(2) }
	ACCESS read-write
	STATUS deprecated
	DESCRIPTION
		"The Status of the Entry valid(1) or
		invalid(2), writing invalid(2) will
		delete the entry from the table"
	::= {trapEntry 1}

trapDestination OBJECT-TYPE
	SYNTAX IpAddress
	ACCESS read-only
	STATUS deprecated
	DESCRIPTION
		"The Destination IP Address"
	::= {trapEntry 2}

trapCommunity OBJECT-TYPE
	SYNTAX DisplayString (SIZE (0..32))
	ACCESS read-write
	STATUS deprecated
	DESCRIPTION
		"SNMP Community to be used to send traps
		 to destination trapDestination"
	::= {trapEntry  3}

trapSubject OBJECT-TYPE
	SYNTAX OBJECT IDENTIFIER
	ACCESS read-write
	STATUS deprecated
	DESCRIPTION
		"SNMP Subject Party used to generate traps
		to destination trapDestination"
	::= {trapEntry  4}

trapCategory OBJECT-TYPE
	SYNTAX	INTEGER
	ACCESS read-write
	STATUS deprecated
	DESCRIPTION
		"32 Bit Mask indicating which Trap categories that the
		snmpTrapDestination is interested in.

		'00000001'h - High Priority Configuration Traps
		'00000002'h - Low Priority Configuration Traps
		'00000004'h - High Priority Security Traps
		'00000008'h - Low Priority Security Traps
		'00000010'h - Alarms & Polling Traps
		'00000020'h - Regular Heartbeat Traps
		'00000040'h - End Station Table Traps
		'00000080'h - reserved
		'00000100'h - Physical Entity Traps
		'00000200'h - Facility Traps
		'00000400'h - Service Related Traps

		A value of 0xFFFFFFFF enables all traps."
	::= {trapEntry  5}

trapThrottle OBJECT-TYPE
	SYNTAX INTEGER
	ACCESS read-write
	STATUS deprecated
	DESCRIPTION
		"The Maximum rate at which that trapDestination is willing to
		receive traps, specified as the minimum interval in
		milliseconds between traps.  A value of zero indicates that
		no trap throttling is required."
	::= {trapEntry  6}

snmpTrapTable OBJECT-TYPE
	SYNTAX SEQUENCE OF SnmpTrapEntry
	ACCESS not-accessible
	STATUS mandatory
	DESCRIPTION
		"This table can store the destination addresses of SNMP
		managers that wish to receive traps from this device."
	::= {localSnmp 2}

snmpTrapEntry OBJECT-TYPE
	SYNTAX SnmpTrapEntry
	ACCESS not-accessible
	STATUS mandatory
	DESCRIPTION
		"This table can store the destination addresses of SNMP
		managers that wish to receive traps from this device."
	INDEX	{ snmpTrapIndex }
	::= { snmpTrapTable 1}

SnmpTrapEntry ::= SEQUENCE {
	snmpTrapIndex
		INTEGER,
	snmpTrapDestination
		DisplayString,
	snmpTrapProtocol
		INTEGER,
	snmpTrapCommunity
		DisplayString,
	snmpTrapCategory
		OCTET STRING,
	snmpTrapThrottle
		INTEGER,
        snmpTrapRowStatus
                INTEGER
}

snmpTrapIndex OBJECT-TYPE
        SYNTAX  INTEGER (1..255)
	ACCESS	read-only
	STATUS	mandatory
	DESCRIPTION
		"This is the unique identifier for this row in the snmpTrapTable.
		When creating a new row, a manager can read the value of the
		snmpTrapNextFreeIndex object and (if non-zero) can use this value
		as the index of the new row to be created.

		The actual number of rows that can be created on any particular
                device depends on the memory and processing resources available
                at the time."
	::= {snmpTrapEntry 1}

snmpTrapDestination OBJECT-TYPE
	SYNTAX DisplayString (SIZE(0..50))
	ACCESS read-write
	STATUS mandatory
	DESCRIPTION
		"This DisplayString is the network address of the device to
                which SNMP traps will be sent. This is an IP or IPX address.
		The following formats can be used.
                IP      nnn.nnn.nnn.nnn - dotted format
                IPX     AABBCCDD:AABBCCDDEEFF - network : node

		Destination addresses must be unique within this table. An
		error is returned if an attempt is made to add a duplicate
		address."
	::= {snmpTrapEntry 2}

snmpTrapProtocol OBJECT-TYPE
	SYNTAX	INTEGER	{
			unknown (1),
			ip (2),
			ipx (3)
			}
	ACCESS	read-only
	STATUS	mandatory
	DESCRIPTION
		"This defines the transport protocol to use when sending
		an SNMP trap.

                At present, this value is determined by the format/value of
		snmpTrapDestionation which is currently un-ambiguous and
		so this object is read-only."
	::= {snmpTrapEntry 3}

snmpTrapCommunity OBJECT-TYPE
	SYNTAX DisplayString (SIZE (0..32))
	ACCESS read-write
	STATUS mandatory
	DESCRIPTION
		"SNMP Community String to be used when sending Traps
		 to this destination."
	::= {snmpTrapEntry  4}

snmpTrapCategory OBJECT-TYPE
	SYNTAX	OCTET STRING (SIZE(4))
	ACCESS read-write
	STATUS mandatory
	DESCRIPTION
		"32 Bit Mask indicating which Trap categories that the
		snmpTrapDestination is interested in.

		'00000001'h - High Priority Configuration Traps
		'00000002'h - Low Priority Configuration Traps
		'00000004'h - High Priority Security Traps
		'00000008'h - Low Priority Security Traps
		'00000010'h - Alarms & Polling Traps
		'00000020'h - Regular Heartbeat Traps
		'00000040'h - End Station Table Traps
		'00000080'h - reserved
		'00000100'h - Physical Entity Traps
		'00000200'h - Facility Traps
		'00000400'h - Service Related Traps

		A value of 0xFFFFFFFF enables all traps."
	::= {snmpTrapEntry  5}

snmpTrapThrottle OBJECT-TYPE
	SYNTAX INTEGER (0..99999)
	ACCESS read-write
	STATUS mandatory
	DESCRIPTION
		"The maximum rate at which that snmpTrapDestination is willing to
		receive traps, specified as the minimum interval in
		milliseconds between traps. For example, a value of 2000 will
		limit traps sent to this destination to one trap every 2
		seconds. A value of zero indicates that no trap throttling is
		required."
	DEFVAL { 10 }
	::= {snmpTrapEntry  6}

snmpTrapRowStatus	OBJECT-TYPE
     SYNTAX       INTEGER {
                               -- the following two values are states:
                               -- these values may be read or written
                               active(1),
                               notInService(2),

                               -- the following value is a state:
                               -- this value may be read, but not written
                               notReady(3),

                               -- the following three values are
                               -- actions: these values may be written,
                               --   but are never read
                               createAndGo(4),
                               createAndWait(5),
                               destroy(6)
                           }
	ACCESS	read-write
	STATUS	mandatory
	DESCRIPTION
		"The SNMPv2 RowStatus convention.

		  Notes: Because this is such a simple table:-
		  1) Writing any data to a destroyed row, changes its state to active.
		  2) There is no notReady or notInService state. Each row is either
		  active or destroyed."
	::= {snmpTrapEntry  7}

snmpTrapNextFreeIndex       OBJECT-TYPE
        SYNTAX  INTEGER (0..255)
        ACCESS  read-only
        STATUS  mandatory
        DESCRIPTION
                "Indicates the the next value of snmpTrapIndex which can be used
                to create a new trap destination entry. This value is zero if
                there are no free rows in the table."
	::= {localSnmp 3}

	-- define the standard snmp Traps  and any pdd specific standard snmp
	-- traps.

--          coldStart TRAP-TYPE
--              ENTERPRISE  snmp
--              DESCRIPTION
--                          "A coldStart trap signifies that the sending
--                          protocol entity is reinitializing itself such
--                          that the agent's configuration or the protocol
--                          entity implementation may be altered."
--              ::= 0
--
--          warmStart TRAP-TYPE
--              ENTERPRISE  snmp
--              DESCRIPTION
--                          "A warmStart trap signifies that the sending
--                          protocol entity is reinitializing itself such
--                          that neither the agent configuration nor the
--                          protocol entity implementation is altered."
--              ::= 1
--
--          linkDown TRAP-TYPE
--              ENTERPRISE  snmp
--              VARIABLES   { ifIndex }
--              DESCRIPTION
--                          "A linkDown trap signifies that the sending
--                          protocol entity recognizes a failure in one of
--                          the communication links represented in the
--                          agent's configuration."
--              ::= 2
--
--          linkUp TRAP-TYPE
--              ENTERPRISE  snmp
--              VARIABLES   { ifIndex }
--              DESCRIPTION
--                          "A linkUp trap signifies that the sending
--                          protocol entity recognizes that one of the
--                          communication links represented in the agent's
--                          configuration has come up."
--              ::= 3
--
--          authenticationFailure TRAP-TYPE
--              ENTERPRISE  snmp
--              DESCRIPTION
--                          "An authenticationFailure trap signifies that
--                          the sending protocol entity is the addressee
--                          of a protocol message that is not properly
--                          authenticated.  While implementations of the
--                          SNMP must be capable of generating this trap,
--                          they must also be capable of suppressing the
--                          emission of such traps via an implementation-
--                          specific mechanism."
--              ::= 4
-- -----------------------------------------------------------------------------
--		 Novell's IPX MIB
-- -----------------------------------------------------------------------------

-- This MIB defines the management information for a system using the IPX
-- protocol.  The MIB consists of four groups:
--
--    1.  System Group - contains general information about all instances
--                       of IPX on the system
--
--    2.  Circuit Group - contains information about all circuits used by
--                        IPX on the system
--
--    3.  Forwarding Group - contains generic routing information that
--                           must be provided by any IPX routing protocol.
--
--    4.  Services Group - contains information about all known services.
--
-- The MIB is designed to support multiple instances of the IPX
-- protocol on one system via a system instance identifier which is the
-- primary index for every table in this MIB.
--
-- This MIB is designed to provide a basic framework for the management
-- of systems implementing the IPX protocol.  Additional MIBs may be
-- created (especially in the area of IPX routing protocols) to contain
-- more specific information.  Whenever possible, these additional MIBs
-- should follow the format of this IPX MIB.  Information in these MIBs
-- should be linked to this MIB via the use of the system instance
-- identifier mentioned above.

novell  OBJECT IDENTIFIER ::= { enterprises 23 }
mibDoc  OBJECT IDENTIFIER ::= { novell 2 }
ipx     OBJECT IDENTIFIER ::= { mibDoc 5 }

-- Groups

ipxSystem OBJECT IDENTIFIER ::= {ipx 1}
ipxCircuit OBJECT IDENTIFIER ::= {ipx 2}
ipxForwarding OBJECT IDENTIFIER ::= {ipx 3}
ipxServices OBJECT IDENTIFIER ::= {ipx 4}
ipxTraps OBJECT IDENTIFIER ::= {ipx 5}

-- Types
-- NetNumber ::= OCTET STRING (SIZE(4))

-- System Group
--   This group contains global information about each instance of IPX
--   running on one system.

-- Basic System Table
--   This table contains one entry for each instance of IPX running on
--   the system.  It contains the management information that should
--   be made available by all implementations of the IPX protocol.

ipxBasicSysTable OBJECT-TYPE
	SYNTAX	SEQUENCE OF IpxBasicSysEntry
	ACCESS	not-accessible
	STATUS	mandatory
	DESCRIPTION
	"The IPX System Table - basic information."
	::= { ipxSystem 1 }

ipxBasicSysEntry	OBJECT-TYPE
	SYNTAX	IpxBasicSysEntry
	ACCESS	not-accessible
	STATUS	mandatory
	DESCRIPTION
	"Each entry corresponds to one instance of IPX running on the system."
	INDEX	{ ipxBasicSysInstance }
	::= { ipxBasicSysTable 1 }

IpxBasicSysEntry ::= SEQUENCE {
                        ipxBasicSysInstance
                           INTEGER,
                        ipxBasicSysExistState
                           INTEGER,
                        ipxBasicSysNetNumber
                           OCTET STRING,
                        ipxBasicSysNode
                           OCTET STRING,
                        ipxBasicSysName
                           OCTET STRING,
                        ipxBasicSysInReceives
                           Counter,
                        ipxBasicSysInHdrErrors
                           Counter,
                        ipxBasicSysInUnknownSockets
                           Counter,
                        ipxBasicSysInDiscards
                           Counter,
                        ipxBasicSysInBadChecksums
                           Counter,
                        ipxBasicSysInDelivers
                           Counter,
                        ipxBasicSysNoRoutes
                           Counter,
                        ipxBasicSysOutRequests
                           Counter,
                        ipxBasicSysOutMalformedRequests
                           Counter,
                        ipxBasicSysOutDiscards
                           Counter,
                        ipxBasicSysOutPackets
                           Counter,
                        ipxBasicSysConfigSockets
                           INTEGER,
                        ipxBasicSysOpenSocketFails
                           Counter
                    }

ipxBasicSysInstance	OBJECT-TYPE
	SYNTAX	INTEGER
	ACCESS	read-only
	STATUS	mandatory
	DESCRIPTION "The unique identifier of the instance of IPX to which this
                row corresponds.  This value may be written only when
                creating a new entry in the table."
	::= { ipxBasicSysEntry 1 }

ipxBasicSysExistState	OBJECT-TYPE
	SYNTAX	INTEGER {
			off(1),
			on(2)
			}
	ACCESS	read-write
	STATUS	mandatory
  	DESCRIPTION "The validity of this entry in the IPX system table.
                Setting this field to off indicates that this entry may be
                deleted from the system table at the IPX implementation's
                discretion."
	::= { ipxBasicSysEntry 2 }

ipxBasicSysNetNumber	OBJECT-TYPE
	SYNTAX	OCTET STRING (SIZE(4))
	ACCESS	read-write
	STATUS	mandatory
	DESCRIPTION
		"The network number portion of the IPX address of this system."
	::= { ipxBasicSysEntry 3 }

ipxBasicSysNode	OBJECT-TYPE
	SYNTAX	OCTET STRING (SIZE(6))
	ACCESS	read-write
	STATUS	mandatory
	DESCRIPTION
		"The node number portion of the IPX address of this system."
	::= { ipxBasicSysEntry 4 }

ipxBasicSysName	OBJECT-TYPE
	SYNTAX	OCTET STRING (SIZE(0..48))
	ACCESS	read-write
	STATUS	mandatory
	DESCRIPTION
		"The readable name for this system."
	::= { ipxBasicSysEntry 5 }

ipxBasicSysInReceives	OBJECT-TYPE
	SYNTAX	Counter
	ACCESS	read-only
	STATUS	mandatory
	DESCRIPTION
		"The total number of IPX packets received, including those
		received in error."
	::= { ipxBasicSysEntry 6 }

ipxBasicSysInHdrErrors	OBJECT-TYPE
	SYNTAX	Counter
	ACCESS	read-only
	STATUS	mandatory
	DESCRIPTION
		"The number of IPX packets discarded due to errors in
		their headers, including any IPX packets with a size less
		than the minimum of 30 bytes."
	::= { ipxBasicSysEntry 7 }

ipxBasicSysInUnknownSockets	OBJECT-TYPE
	SYNTAX	Counter
	ACCESS	read-only
	STATUS	mandatory
	DESCRIPTION
		"The number of IPX packets discarded because the
		destination socket was not open."
	::= { ipxBasicSysEntry 8 }

ipxBasicSysInDiscards	OBJECT-TYPE
	SYNTAX	Counter
	ACCESS	read-only
	STATUS	mandatory
	DESCRIPTION
		"The number of IPX packets received but discarded due to
		reasons other than those accounted for by
		ipxBasicSysInHdrErrors, ipxBasicSysInUnknownSockets,
		ipxAdvSysInDiscards, and ipxAdvSysInCompressDiscards."
	::= { ipxBasicSysEntry 9 }

ipxBasicSysInBadChecksums	OBJECT-TYPE
	SYNTAX	Counter
	ACCESS	read-only
	STATUS	mandatory
	DESCRIPTION
		"The number of IPX packets received with incorrect checksums."
	::= { ipxBasicSysEntry 10 }

ipxBasicSysInDelivers	OBJECT-TYPE
	SYNTAX	Counter
	ACCESS	read-only
	STATUS	mandatory
	DESCRIPTION
		"The total number of IPX packets delivered locally,
		including packets from local applications."
	::= { ipxBasicSysEntry 11 }

ipxBasicSysNoRoutes	OBJECT-TYPE
	SYNTAX	Counter
	ACCESS	read-only
	STATUS	mandatory
	DESCRIPTION
		"The number of times no route to a destination was found."
	::= { ipxBasicSysEntry 12 }

ipxBasicSysOutRequests	OBJECT-TYPE
	SYNTAX	Counter
	ACCESS	read-only
	STATUS	mandatory
	DESCRIPTION
		"The number of IPX packets supplied locally for
		transmission, not including any packets counted in
		ipxAdvForwPackets."
	::= { ipxBasicSysEntry 13 }

ipxBasicSysOutMalformedRequests	OBJECT-TYPE
	SYNTAX	Counter
	ACCESS	read-only
	STATUS	mandatory
	DESCRIPTION
		"The number of IPX packets supplied locally that contained
		errors in their structure."
	::= { ipxBasicSysEntry 14 }

ipxBasicSysOutDiscards	OBJECT-TYPE
	SYNTAX	Counter
	ACCESS	read-only
	STATUS	mandatory
	DESCRIPTION
		"The number of outgoing IPX packets discarded due to
		reasons other than those accounted for in
		ipxBasicSysOutMalformedDiscards, ipxAdvSysOutFiltered,
		and ipxAdvSysOutCompressDiscards."
	::= { ipxBasicSysEntry 15 }

ipxBasicSysOutPackets	OBJECT-TYPE
	SYNTAX	Counter
	ACCESS	read-only
	STATUS	mandatory
	DESCRIPTION
		"The total number of IPX packets transmitted."
	::= { ipxBasicSysEntry 16 }

ipxBasicSysConfigSockets	OBJECT-TYPE
	SYNTAX	INTEGER
	ACCESS	read-only
	STATUS	mandatory
	DESCRIPTION
		"The configured maximum number of IPX sockets that may
		be open at one time."
	::= { ipxBasicSysEntry 17 }

ipxBasicSysOpenSocketFails	OBJECT-TYPE
	SYNTAX	Counter
	ACCESS	read-only
	STATUS	mandatory
	DESCRIPTION
		"The number of IPX socket open calls which failed."
	::= { ipxBasicSysEntry 18 }

-- Advanced System Group
--	This table contains one entry for each instance of IPX running on
--	the system. It contains the advanced management information that`
--	may not be available from all implementations.

ipxAdvSysTable OBJECT-TYPE
	SYNTAX	SEQUENCE OF IpxAdvSysEntry
	ACCESS	not-accessible
	STATUS	mandatory
	DESCRIPTION
	"The IPX System Table - advanced information."
	::= { ipxSystem 2 }

ipxAdvSysEntry	OBJECT-TYPE
	SYNTAX	IpxAdvSysEntry
	ACCESS	not-accessible
	STATUS	mandatory
	DESCRIPTION
	"Each entry corresponds to one instance of IPX running on the system."
	INDEX	{ ipxAdvSysInstance }
	::= { ipxAdvSysTable 1 }

IpxAdvSysEntry ::= SEQUENCE {
		ipxAdvSysInstance		INTEGER,
		ipxAdvSysMaxPathSplits		INTEGER,
		ipxAdvSysMaxHops		INTEGER,
		ipxAdvSysTooManyHops		Counter,
		ipxAdvSysInFiltered		Counter,
		ipxAdvSysCompressDiscards	Counter,
		ipxAdvSysNETBIOSPackets		Counter,
		ipxAdvSysForwPackets		Counter,
		ipxAdvSysOutFiltered		Counter,
		ipxAdvSysOutCompressDiscards	Counter,
		ipxAdvSysCircCount		Counter,
		ipxAdvSysDestCount		Counter,
		ipxAdvSysServCount		Counter
	}

ipxAdvSysInstance	OBJECT-TYPE
	SYNTAX	INTEGER
	ACCESS	read-write
	STATUS	mandatory
	DESCRIPTION
		"The unique identifer of the instance of IPX to which this
		row corresponds. This value may be written only when
		creating a new entry in the table."
	::= { ipxAdvSysEntry 1 }

ipxAdvSysMaxPathSplits	OBJECT-TYPE
	SYNTAX	INTEGER (1..32)
	ACCESS	read-write
	STATUS	mandatory
	DESCRIPTION
		"The maximum number of paths with equal routing metric
		value which this instance of the IPX my split
		between when forwarding packets."
	DEFVAL	{ 1 }
	::= { ipxAdvSysEntry 2 }

ipxAdvSysMaxHops	OBJECT-TYPE
	SYNTAX	INTEGER
	ACCESS	read-write
	STATUS	mandatory
	DESCRIPTION
		"The maximum number of hops a packet may take."
	DEFVAL	{ 64 }
	::= { ipxAdvSysEntry 3 }

ipxAdvSysTooManyHops	OBJECT-TYPE
	SYNTAX	Counter
	ACCESS	read-only
	STATUS	mandatory
	DESCRIPTION
		"The number of IPX packets discarded due to exceeding the
		maximum hop count."
	::= { ipxAdvSysEntry 4 }

ipxAdvSysInFiltered	OBJECT-TYPE
	SYNTAX	Counter
	ACCESS	read-only
	STATUS	mandatory
	DESCRIPTION
		"The number of incoming IPX packets discarded due to filtering."
	::= { ipxAdvSysEntry 5 }

ipxAdvSysCompressDiscards	OBJECT-TYPE
	SYNTAX	Counter
	ACCESS	read-only
	STATUS	mandatory
	DESCRIPTION
		"The number of incoming IPX packets discarded due to
		decompression errors."
	::= { ipxAdvSysEntry 6 }

ipxAdvSysNETBIOSPackets	OBJECT-TYPE
	SYNTAX	Counter
	ACCESS	read-only
	STATUS	mandatory
	DESCRIPTION
		"The number of NETBIOS packets received."
	::= { ipxAdvSysEntry 7 }

ipxAdvSysForwPackets	OBJECT-TYPE
	SYNTAX	Counter
	ACCESS	read-only
	STATUS	mandatory
	DESCRIPTION
		"The number of IPX packets forwarded."
	::= { ipxAdvSysEntry 8 }

ipxAdvSysOutFiltered	OBJECT-TYPE
	SYNTAX	Counter
	ACCESS	read-only
	STATUS	mandatory
	DESCRIPTION
		"The number of outgoing IPX packets discarded due to filtering."
	::= { ipxAdvSysEntry 9 }

ipxAdvSysOutCompressDiscards	OBJECT-TYPE
	SYNTAX	Counter
	ACCESS	read-only
	STATUS	mandatory
	DESCRIPTION
		"The number of outgoing IPX packets discarded due to
		compression errors."
	::= { ipxAdvSysEntry 10 }

ipxAdvSysCircCount	OBJECT-TYPE
	SYNTAX Counter
	ACCESS	read-only
	STATUS	mandatory
	DESCRIPTION
		"The number of circuits known to this instance of IPX."
	::= { ipxAdvSysEntry 11 }

ipxAdvSysDestCount	OBJECT-TYPE
	SYNTAX	Counter
	ACCESS	read-only
	STATUS	mandatory
	DESCRIPTION
		"The number of currently reachable destinations known to
		this instance of IPX."
	::= { ipxAdvSysEntry 12 }

ipxAdvSysServCount	OBJECT-TYPE
	SYNTAX	Counter
	ACCESS	read-only
	STATUS	mandatory
	DESCRIPTION
		"The number of services known to this instance of IPX."
	::= { ipxAdvSysEntry 13 }

-- Circuit Group
--	This group contains management information for each circuit known
--	to this system.

-- Circuit Table
--	The Circuit table contains an entry for each circuit known to the
--	system.

-- The Circuit group is not relevant to this device, and so is not presented here.

-- Forwarding Group
--	This group provides a representation of the forwarding database used
--	by all instances of IPX on the system.

-- Destination Table
--	The Destination table contains information about all known
--	destinations. The routing information shown in this table represents
--	the path currently being used to reach the destination.

-- Static Routes Table
--	This table contains the information about all the static routes
--	defined. There may be more than one static route to any given
--	destination. Only the route currently being used will also be
--	present in the Destination Table defined above.

-- The Forwarding group is not relevant to this device, and so is not presented here.

-- Services Group
--	The Services group contains management information for all known
--	services.

-- Services Table
--	This table contains the services information indexed by service
--	name and type.

-- Destination Services Table
--	This table contains the services information indexed by address,
--	name, and type.

-- Static Services Table
--	This table contains information for all services reached via a
--	static route.

-- The Services group is not relevant to this device, and so is not presented here.

-- Traps Group
--	This group describes the traps defined for IPX.

-- The Trap group is not relevant to this device, and so is not presented here.

-- End of Novell's IPX MIB.
-- ****************************************************************************
-- RESILIENCE
-- ****************************************************************************
resTable OBJECT-TYPE
	SYNTAX 		SEQUENCE OF ResTableEntry
	ACCESS		not-accessible
	STATUS		mandatory
	DESCRIPTION ""
	::= { mrmResilience 1 }

resTableEntry OBJECT-TYPE
	SYNTAX		ResTableEntry
	ACCESS		not-accessible
	STATUS		mandatory
	DESCRIPTION "
An MSH may be configured to contain a number of 'resilient pairs'.  These
are 802.3 point to point connections, e.g. UTP, that allow two repeaters to
be connected together in a resilient configuration. In such a configuration
one of the two ports is nominated the 'main' port while the other is the
'standby' port. One of these two ports is enabled and is the current active
port. The other is present in case of failure of the active port. Such a
failure is detected by the MSH and a switch performed.

There are a couple of rules that must apply to a resilient pair definition
before that definition becomes a valid resilient pair. Firstly both ports
must be on the same repeater. Secondly the standby port must be configured
to be 'disabled on boot'. That is it must recover from a power failure in a
disabled state. This prevents loops in the network.

Several tables control the resilient repeater configuration for the MSH.
This is the first. This is the main table and allows the creation and
deletion of pairs and provides status control and information. The
information in this table is indexed on the repeater number and the slot/port
location of the main port.

To create a new resilient pair simply write any writeable object indexed on
the main port. This will create a new entry in the table which has the state
'invalid' (read resPairState). Having created the row, write to the other
parameters specifying valid information. When all the parameters are valid
the resPairState will become 'operational'. In this state the pair will correctly
operate as a resilient pair. If any of the attributes in the table change so
that the pair in no linger valid this will be reflected in the resPortState
parameter.

To delete a resilient pair, write 'delete' to resPairAction."
	INDEX		{	resRepeater,
				resMainSlot,
				resMainPort
			}
	::= { resTable 1 }

	ResTableEntry ::= SEQUENCE {
		resRepeater		  INTEGER,
		resMainSlot		  INTEGER,
		resMainPort		  INTEGER,
		resMainState		  INTEGER,
		resStandbySlot		  INTEGER,
		resStandbyPort		  INTEGER,
		resStandbyState		  INTEGER,
		resPairState		  INTEGER,
                resPairModificationStatus INTEGER,
		resPairAction		  INTEGER,
		resPairEnable		  INTEGER

	}

resRepeater		OBJECT-TYPE
	SYNTAX	INTEGER
	ACCESS	read-only
	STATUS	mandatory
	DESCRIPTION "
A resilient pair must be attached to one of the repeaters in the chassis.
This is part of the index value required to access this table."
	::= { resTableEntry 1 }

resMainSlot		OBJECT-TYPE
	SYNTAX	INTEGER
	ACCESS	read-only
	STATUS	mandatory
	DESCRIPTION "
This is the second key in the index to this table. This is the slot number
of the main port in this pair."
	::= { resTableEntry 2 }

resMainPort		OBJECT-TYPE
	SYNTAX	INTEGER
	ACCESS	read-only
	STATUS	mandatory
	DESCRIPTION "
This is the final, key used to index entries in this table. It is the port
number of the main port in the pair."
	::= { resTableEntry 3 }

resMainState	OBJECT-TYPE
	SYNTAX	INTEGER { failed (1), ok(2), ok-and-active(3) }
	ACCESS	read-only
	STATUS	mandatory
	DESCRIPTION "
Each port in a pair is constantly monitored for signs of failure. Failure
information is used to automatically change the active port from main to
standby or vice-versa. Each port may be in one of three states. Failed
indicates there is a loss of signal on this port. A port in this state
cannot be active. Secondly OK. This state indicates that the port is capable
of carrying traffic but is at the moment acting in the role of backup link.
The other port in this pair will be in the OK and Active state.

OK and Active means what it says, this port is capable of carrying traffic
and is so doing at the time this parameter has been read."
	::= { resTableEntry 4 }

resStandbySlot		OBJECT-TYPE
	SYNTAX	INTEGER
	ACCESS	read-write
	STATUS	mandatory
	DESCRIPTION "
This is the slot number of the standby port for this pair. The port must be
present on the same repeater as the main port and so this information is not
duplicated."
	::= { resTableEntry 5 }

resStandbyPort		OBJECT-TYPE
	SYNTAX	INTEGER
	ACCESS	read-write
	STATUS	mandatory
	DESCRIPTION "This is the port number of the standby port."
	::= { resTableEntry 6 }

resStandbyState		OBJECT-TYPE
	SYNTAX	INTEGER { failed (1), ok(2), ok-and-active(3) }
	ACCESS	read-only
	STATUS	mandatory
	DESCRIPTION "
Each port in a pair is constantly monitored for signs of failure. Failure
information is used to automatically change the active port from main to
standby or vice-versa. Each port may be in one of three states. Failed
indicates there is a loss of signal on this port. A port in this state
cannot be active. Secondly OK. This state indicates that the port is capable
of carrying traffic but is at the moment acting in the role of backup link.
The other port in this pair will be in the OK and Active state.

OK and Active means what it says, this port is capable of carrying traffic
and is so doing at the time this parameter has been read."
	::= { resTableEntry 7 }

resPairState	OBJECT-TYPE
	SYNTAX	INTEGER {
		invalid			(1),
		operational		(2)
	}
	ACCESS	read-only
	STATUS	mandatory
	DESCRIPTION "
Each row in the table is in one of two states, 'invalid' or 'operational'.
If the state is 'invalid', the resilient pair represented by this row is not
active. There are several reasons why this may be the case. Firstly during
the row creation process, not all information necessary may have been provided.
Secondly an operational pair may become invalid because the resilient pair
rules are no longer met because of a change in the MSH configuration. The
rules are that both main and standby ports be on the same repeater and that
the standby port be 'disable on boot'. Changing the standby card, moving one
of the cards to a different repeater are two possible changes that can
invalidate a pair configration.

If the parameters in the row are all valid then the pair becomes
'operational'."
	::= { resTableEntry 8 }

resPairModificationStatus OBJECT-TYPE
	SYNTAX INTEGER {
		under-modification (1),
		stable             (2)
        }
	ACCESS read-write
	STATUS mandatory
	DESCRIPTION "
	This parameter must be set to under-modification before any changes
	are made to an existing configuration. Changes are not applied
	until this parameter is set to stable.
	"
	::= { resTableEntry 9 }

resPairAction	OBJECT-TYPE
	SYNTAX	INTEGER {
		create                  (1),
		delete			(2),
		togglePort		(3)
	}
	ACCESS write-only
	STATUS	mandatory
	DESCRIPTION "
This is object allows the state of a resilient pair to be modified.
The create operation configures the resilient port from this table entry.
The delete operation removes the resilient definitions from this table and
terminates operation of resilience on this pair of ports. The togglePort
operation allows the current active port to be changed to the other port.
This second operation will only take affect if the state of the currently
non-active port is 'OK'."
	::= { resTableEntry 10 }

resPairEnable	OBJECT-TYPE
	SYNTAX	INTEGER {
		enable                  (1),
		disable			(2)
	}
	ACCESS  read-write
	STATUS	mandatory
	DESCRIPTION "
This parameter controls whether the resilient pair is enabled or not.
In the disabled state , both ports of the resilient pair are disabled.
The default value of this parameter is enable
"
	::= { resTableEntry 11 }


-- **********************************************************************
-- **********************************************************************
-- resilient standby mapping table.
-- **********************************************************************
resStandbyMapTable OBJECT-TYPE
	SYNTAX 		SEQUENCE OF ResStandbyMapTableEntry
	ACCESS		not-accessible
	STATUS		mandatory
	DESCRIPTION ""
	::= { mrmResilience 2 }

resStandbyMapTableEntry OBJECT-TYPE
	SYNTAX		ResStandbyMapTableEntry
	ACCESS		not-accessible
	STATUS		mandatory
	DESCRIPTION "
This table is read-only. If provides shortcut information to allow for the
translation of a port number to a corresponding main port number. This value
can then be used to access the main resilience table. Each resilient pair has
two entries in this table, one for the main port and one for the standby
port. The entry for the main port returns the same port, the entry for the
standby port returns the corresponding main port."
	INDEX		{	resSbRepeater,
				resSbSlot,
				resSbPort
			}
	::= { resStandbyMapTable 1 }

	ResStandbyMapTableEntry ::= SEQUENCE {
		resSbRepeater		INTEGER,
		resSbSlot		INTEGER,
		resSbPort		INTEGER,
		resSbType		INTEGER,
		resSbMainSlot		INTEGER,
		resSbMainPort		INTEGER
	}

resSbRepeater OBJECT-TYPE
	SYNTAX	INTEGER
	ACCESS	read-only
	STATUS	mandatory
	DESCRIPTION "
The repeater index of the port being accessed. This is the first of three
indices on this table."
	::= { resStandbyMapTableEntry 1 }

resSbSlot OBJECT-TYPE
	SYNTAX	INTEGER
	ACCESS	read-only
	STATUS	mandatory
	DESCRIPTION "Second index on this table."
	::= { resStandbyMapTableEntry 2 }

resSbPort OBJECT-TYPE
	SYNTAX	INTEGER
	ACCESS	read-only
	STATUS	mandatory
	DESCRIPTION "Third index on this table."
	::= { resStandbyMapTableEntry 3 }

resSbType OBJECT-TYPE
	SYNTAX	INTEGER {
		main		(1),
		standby		(2)
	}
	ACCESS	read-only
	STATUS	mandatory
	DESCRIPTION "
This attribute specifies whether the port indexed is a main or standby port
in the resilient pair table. If the port is neither then there will not be a
row in this table indexed for that port."
	::= { resStandbyMapTableEntry 4 }

resSbMainSlot OBJECT-TYPE
	SYNTAX	INTEGER
	ACCESS	read-only
	STATUS	mandatory
	DESCRIPTION "
This is the slot number of the main port for the pair in which the indexed
port participates. NOTE if the index port is the main port of a pair
(resSbType is 'main') this value will be the same as the index."
	::= { resStandbyMapTableEntry 5 }

resSbMainPort OBJECT-TYPE
	SYNTAX	INTEGER
	ACCESS	read-only
	STATUS	mandatory
	DESCRIPTION "
This is the port number of the main port for the pair in which the indexed
port participates. NOTE if the index port is the main port of a pair
(resSbType is 'main') this value will be the same as the index."
	::= { resStandbyMapTableEntry 6 }

resFlushTable OBJECT-TYPE
	SYNTAX INTEGER
	ACCESS write-only
	STATUS mandatory
	DESCRIPTION "
This parameter causes all entries in the resilience table to be flushed.
Flushing the resilience table does not affect the state of any of the
resilient links or ports. Once the table has been flushed , NO resilient
links are configured.
This parameter is used to ensure that the resilient link table is empty ,
before new resilient links are configured."
	::= { mrmResilience 3 }

-- **********************************************************************
-- Some traps generated by the resilience engine.
-- **********************************************************************
resResilienceSwitch TRAP-TYPE
	ENTERPRISE a3Com
	VARIABLES   { resMainState, resStandbyState }
	DESCRIPTION "
This trap is generated when a change of state of one of the ports in a
resilient pair does not result in a switch of active port. If such a switch
were to occur the resResilienceSwitch would be generated. Generation of
this trap is summarised in the following table:

------------------------------------------------------------------------------
   State        |                         Event
Main    Backup  |Main Fail      |Main OK        |StandBy Fail   |Standby OK
------------------------------------------------------------------------------
Active  OK      |  switch       |  -----        |  state        |  -----
Active  Fail    |  state        |  -----        |  -----        |  state
OK      Active  |  state        |  -----        |  switch       |  -----
Fail    Active  |  -----        |  state        |  state        |  -----
Fail    Fail    |  -----        |  switch       |  -----        |  state
-----------------------------------------------------------------------------

In this table '-----' indicates no trap is sent. 'switch' indicates the
resResilienceSwitch trap is sent and 'state' indicates resStateChange is
sent.

NOTE: The agent in the MSH does not suppress any traps that caused the state
change. For example if the active link is lost then both a 'loss-of-link'
trap AND a resilienceSwitch trap are generated."
	::= 43

resStateChange TRAP-TYPE
	ENTERPRISE a3Com
	VARIABLES   { resMainState, resStandbyState }
	DESCRIPTION "
This trap is generated when a change of state of one of the ports in a
resilient pair does not result in a switch of active port. If such a switch
were to occur the resResilienceSwitch would be generated. Generation of
this trap is summarised in the following table:

------------------------------------------------------------------------------
   State        |                         Event
Main    Backup  |Main Fail      |Main OK        |StandBy Fail   |Standby OK
------------------------------------------------------------------------------
Active  OK      |  switch       |  -----        |  state        |  -----
Active  Fail    |  state        |  -----        |  -----        |  state
OK      Active  |  state        |  -----        |  switch       |  -----
Fail    Active  |  -----        |  state        |  state        |  -----
Fail    Fail    |  -----        |  switch       |  -----        |  state
-----------------------------------------------------------------------------

In this table '-----' indicates no trap is sent. 'switch' indicates the
resResilienceSwitch trap is sent and 'state' indicates resStateChange is
sent.

NOTE: The agent in the MSH does not suppress any traps that caused the state
change. For example if the active link is lost then both a 'loss-of-link'
trap AND a resilienceSwitch trap are generated."
	::= 44

--
--	Power Supply MIB
--

powerStackPackage	OBJECT IDENTIFIER ::= { powerSupply 1}

powerStackBackupPresent OBJECT-TYPE
	SYNTAX			INTEGER {
					notPresent(1),
					present(2)
					}
	ACCESS			read-only
	STATUS			mandatory
	DESCRIPTION
				"Indicates whether a Resilient Backup Power Supply is
				being used by this stack of units."

	::=  { powerStackPackage 1 }

powerStackBackupData OBJECT-TYPE
	SYNTAX			OCTET STRING (SIZE(1..8))
	ACCESS			read-only
	STATUS			mandatory
	DESCRIPTION
				"Supplies all the information about the power supplies
				attached to each unit in a stack. This object is
				provided to speed up processing by Network Manager
				applications.
				There is one octet for each unit in the stack. Each
				octet contains the following information:

					Bit 1:	RBS applicable	( 1 = Yes, 0 = No )
					Bit 2:	RBS present	( 1 = Yes, 0 = No )
					Bit 3:	RBS status	( 1 = fault, 0 = OK )

				( RBS = Resilient Backup Power Supply )

				If Bit 1 is zero, this means that an RBS cannot be attached
				to this unit and all the other bits will be zero."

	::=  { powerStackPackage 2 }

powerStackTable		OBJECT-TYPE
			SYNTAX			SEQUENCE OF PowerStackTableEntry
			ACCESS			not-accessible
			STATUS			mandatory
			DESCRIPTION
			"This table provides power supply status information for all
			units in an FMS stack."
			::= { powerStackPackage 3 }

powerStackTableEntry	OBJECT-TYPE
			SYNTAX			PowerStackTableEntry
			ACCESS			not-accessible
			STATUS			mandatory
			DESCRIPTION
			"Each Table entry provides information for a single unit in the
			stack."
			INDEX			{ powerStackTableIndex }
			::= { powerStackTable 1 }

			PowerStackTableEntry ::= SEQUENCE {
						powerStackTableIndex	INTEGER,
						powerStackRBSPresent	INTEGER,
						powerStackRBSStatus 	INTEGER
						}

powerStackTableIndex		OBJECT-TYPE
			SYNTAX			INTEGER
			ACCESS			read-only
			STATUS			mandatory
			DESCRIPTION
			"Identifies which FMS unit (1-8) the table entry relates to."
			::= { powerStackTableEntry  1 }

powerStackRBSPresent		OBJECT-TYPE
			SYNTAX			INTEGER	{
							rbsNotApplicable	(1),
							rbsPresent		(2),
							rbsNotPresent		(3)
							}
			ACCESS			read-only
			STATUS			mandatory
			DESCRIPTION
			"This indicates whether a Resilient Power Supply is attached to this unit.
			A value of rbsNotApplicable indicates that this unit does not support
			Resilient Power Supplies,
			rbsPresent indicates that a RBS is attached and in use,
			rbsNotPresent indicates that this unit is using it's internal supply."
			::= { powerStackTableEntry  2 }

powerStackRBSStatus		OBJECT-TYPE
			SYNTAX			INTEGER	{
							rbsNotApplicable	(1),
							rbsOK			(2),
							rbsFault		(3)
							}
			ACCESS			read-only
			STATUS			mandatory
			DESCRIPTION
			"This indicates the status of a Resilient Power Supply attached to this unit.
			A value of rbsNotApplicable indicates that this unit does not support
			Resilient Power Supplies,
			rbsok indicates that the attached RBS is functioning with no faults,
			rbsFault indicates that the RBS has a fault e.g. fan has failed or switched
			power supplies."

			::= { powerStackTableEntry  3 }

powerStackBackupFault	TRAP-TYPE
        ENTERPRISE              a3Com
        DESCRIPTION
                                "This trap indicates that a Resilient Backup Power Supply
				connected to this repeater has developed a fault. This fault has
				not stopped the RBS from functioning e.g. fan failed, unit
				overheating, or unit has switched to resilient power supply."
        ::= 			63

powerStackBackupRecovered	TRAP-TYPE
        ENTERPRISE              a3Com
        DESCRIPTION
                                "This trap indicates that a Resilient Backup Power Supply
				connected to this repeater has recovered from and outstanding
				fault."
        ::= 			64


       END
