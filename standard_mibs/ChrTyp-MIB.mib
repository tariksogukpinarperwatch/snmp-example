-- Unknown content
-- Circitor
ChrTyp-MIB DEFINITIONS ::= BEGIN

TruthValue ::= INTEGER	 { false(0), true(1) }

		AdminStatus	::=	INTEGER	{
				undefined(1),
				disabled(2),
				enabled(3)
			 }
			 
			     OperStatus ::= INTEGER {
			operStateDown(0),
                        operStateUP(1),
                        operStateAbsent(2),
			operStateStandby(3)
                        }

END
