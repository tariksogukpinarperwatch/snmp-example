-- extracted from draft-ietf-eos-snmpxproto-mib-03.txt
-- at Fri Aug 30 06:10:05 2002

   IANA-SNMP-PROTOCOL-TC DEFINITIONS ::= BEGIN
   IMPORTS
    MODULE-IDENTITY, mib-2  FROM SNMPv2-SMI
    TEXTUAL-CONVENTION      FROM  SNMPv2-TC;

   ianaSnmpProtoNumbers MODULE-IDENTITY
          LAST-UPDATED "200202200000Z"
          ORGANIZATION "IANA"
          CONTACT-INFO
              "Postal:    Internet Assigned Numbers Authority
                          Internet Corporation for Assigned Names
                           and Numbers
                          4676 Admiralty Way, Suite 330
                          Marina del Rey, CA 90292-6601
                          USA

              Tel:    +1  310-823-9358
              E-Mail: iana@iana.org"
          DESCRIPTION
              "The MIB module defines textual conventions for use
              in identifying SNMP protocol operations."
          ::= { mib-2 1 }

   -- IANA
	IANASnmpProtocol ::= TEXTUAL-CONVENTION
      STATUS current
      DESCRIPTION
        "Standard SNMP protocol operations."
      SYNTAX BITS
        {
        getRequest (0),
        getNextRequest (1),
        getBulkRequest (2),
        response (3),
        setRequest (4),
        informRequest (5),
        snmpV2Trap (6),
        report (7)
        }
--		  END

-- NOTE: this END was not present in draft-ietf-eos-snmpxproto-mib-03.txt,
-- but this does appear to be the end of the MIB.
-- (the next line is '6. Definitions')


END

-- 
--   Copyright (C) The Internet Society (2002). All Rights Reserved.
-- 
--   This document and translations of it may be copied and furnished to
--   others, and derivative works that comment on or otherwise explain it
--   or assist in its implementation may be prepared, copied, published
--   and distributed, in whole or in part, without restriction of any kind,
--   provided that the above copyright notice and this paragraph are
--   included on all such copies and derivative works.  However, this
--   document itself may not be modified in any way, such as by removing
--   the copyright notice or references to the Internet Society or other
--   Internet organizations, except as needed for the  purpose of
--   developing Internet standards in which case the procedures for
--   copyrights defined in the Internet Standards process must be followed,
--   or as required to translate it into languages other than English.
-- 
--   The limited permissions granted above are perpetual and will not be
--   revoked by the Internet Society or its successors or assigns.
-- 
--   This document and the information contained herein is provided on an
--   "AS IS" basis and THE INTERNET SOCIETY AND THE INTERNET ENGINEERING
--   TASK FORCE DISCLAIMS ALL WARRANTIES, EXPRESS OR IMPLIED, INCLUDING BUT
--   NOT LIMITED TO ANY WARRANTY THAT THE USE OF THE INFORMATION HEREIN
--   WILL NOT INFRINGE ANY RIGHTS OR ANY IMPLIED WARRANTIES OF
--   MERCHANTABILITY OR FITNESS FOR A PARTICULAR PURPOSE.
