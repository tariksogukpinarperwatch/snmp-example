-- ============================================================================
-- Copyright (C) by  HUAWEI TECHNOLOGIES. All rights reserved.
-- 
-- Description:  
-- Reference:  
-- Version: V1.02
-- History:
-- ============================================================================
	HUAWEI-RMON-MIB DEFINITIONS ::= BEGIN
	 
		IMPORTS
			OBJECT-TYPE,Counter32
				FROM SNMPv2-SMI
			etherStatsEntry
				FROM RMON-MIB;	
	
		hwEtherStatsPktsRecvPause OBJECT-TYPE
			SYNTAX     Counter32
                        UNITS      "Packets"
                        MAX-ACCESS read-only
                        STATUS     current
			DESCRIPTION
				"
				Number of PAUSE frames received by the port"
			::= { etherStatsEntry 65536 }
		
		hwEtherStatsPktsSendPause OBJECT-TYPE
			SYNTAX     Counter32
                        UNITS      "Packets"
                        MAX-ACCESS read-only
                        STATUS     current
			DESCRIPTION
				"
				Number of PAUSE frames send from the port"
			::= { etherStatsEntry 65537 }
			
		hwEtherStatsPkts1519to2047Octets OBJECT-TYPE
			SYNTAX     Counter32
                        UNITS      "Packets"
                        MAX-ACCESS read-only
                        STATUS     current
			DESCRIPTION
				"
				Total number of frames of 1519-2047 bytes"
			::= { etherStatsEntry 65538 }
		
		hwEtherStatsPkts2048to4095Octets OBJECT-TYPE
			SYNTAX     Counter32
                        UNITS      "Packets"
                        MAX-ACCESS read-only
                        STATUS     current
			DESCRIPTION
				"
				Total number of frames of 2048-4095 bytes"
			::= { etherStatsEntry 65539 }
		hwEtherStatsPkts4096to9216Octets OBJECT-TYPE
			SYNTAX     Counter32
                        UNITS      "Packets"
                        MAX-ACCESS read-only
                        STATUS     current
			DESCRIPTION
				"
				Total number of frames of 4096-9216 bytes"
			::= { etherStatsEntry 65540 }		
		hwEtherStatsRecvOctets OBJECT-TYPE
			SYNTAX     Counter32
                        UNITS      "Octets"
                        MAX-ACCESS read-only
                        STATUS     current
			DESCRIPTION
				"
				The total number of the octets received correctly"
			::= { etherStatsEntry 65541 }
	
		hwEtherStatsSendOctets OBJECT-TYPE
			SYNTAX     Counter32
                        UNITS      "Octets"
                        MAX-ACCESS read-only
                        STATUS     current
			DESCRIPTION
				"
				The total number of the octets sent correctly"
			::= { etherStatsEntry 65542 }
		
		hwEtherStatsPktsSendSingleCollision OBJECT-TYPE
			SYNTAX     Counter32
                        UNITS      "Packets"
                        MAX-ACCESS read-only
                        STATUS     current
			DESCRIPTION
				"
				The total number of packets sent correctly after a single collision
				"
			::= { etherStatsEntry 65543 }
			
		hwEtherStatsPktsSendMultiCollision OBJECT-TYPE
			SYNTAX     Counter32
                        UNITS      "Packets"
                        MAX-ACCESS read-only
                        STATUS     current
			DESCRIPTION
				"
				The total number of packets sent correctly after multiple collisions
				"
			::= { etherStatsEntry 65544 }
			
                hwEtherStatsUpDiscardPackets OBJECT-TYPE
			SYNTAX     Counter32
			UNITS      "Packets"
			MAX-ACCESS read-only
			STATUS     current
			DESCRIPTION
				"
				The total number of up stream discarded packets
				"
			::= { etherStatsEntry 65545 }
			
		hwEtherStatsDownDiscardPackets OBJECT-TYPE
			SYNTAX     Counter32
			UNITS      "Packets"
			MAX-ACCESS read-only
			STATUS     current
			DESCRIPTION
				"
				The total number of down stream discarded packets
				"
			::= { etherStatsEntry 65546 } 
						
	END
