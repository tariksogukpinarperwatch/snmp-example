MacIP-MIB DEFINITIONS ::= BEGIN
    IMPORTS
        mgmt, experimental, Counter, IpAddress, enterprises
        FROM RFC1155-SMI
        OBJECT-TYPE
        FROM RFC-1212
		  ATNetworkNumber, DdpNodeAddress FROM APPLETALK-MIB;

-- This MIB module uses the extended OBJECT-TYPE macro
-- as defined in RFC1212
-- MacIP MIB

mib-2 OBJECT IDENTIFIER ::= { mgmt 1 }
appletalk OBJECT IDENTIFIER ::= { mib-2 13 }
apple OBJECT IDENTIFIER ::= { enterprises 63 }
macip OBJECT IDENTIFIER ::= { apple 1 }

macipNumStaticAddresses OBJECT-TYPE
    SYNTAX INTEGER
    ACCESS read-write
    STATUS mandatory
    DESCRIPTION
        "The number of static addresses configured on
        the gateway."
    ::= { macip 1 }

macipStaticRangeStart OBJECT-TYPE
    SYNTAX IpAddress
    ACCESS read-write
    STATUS mandatory
    DESCRIPTION
        "The first IP address in the range of static IP
        addresses configured on the gateway."
    ::= { macip 2 }

macipNumDynamicAddresses OBJECT-TYPE
    SYNTAX INTEGER
    ACCESS read-write
    STATUS mandatory
    DESCRIPTION
        "The number of dynamic addresses configured on
        the gateway."
    ::= { macip 3 }


macipDynamicRangeStart OBJECT-TYPE
    SYNTAX IpAddress
    ACCESS read-write
    STATUS mandatory
    DESCRIPTION
        "The first IP address in the range of dynamic
        IP addresses configured on the gateway."
    ::= { macip 4 }

macipUseIdleTimeOut OBJECT-TYPE
    SYNTAX INTEGER {
        true(1),
        false(2)
    }
    ACCESS read-write
    STATUS mandatory
    DESCRIPTION
        "If true(1), the idle time out value will be
        used to time out dynamic addresses."
    ::= { macip 5 }

macipUseNBPConfirmTimeOut OBJECT-TYPE
    SYNTAX INTEGER {
        true(1),
        false(2)
    }
    ACCESS read-write
    STATUS mandatory
    DESCRIPTION
        "If true(1), the NBP Confirm time out value
        will be used to time out dynamic addresses."
    ::= { macip 6 }

macipUsePINGTimeOut OBJECT-TYPE
    SYNTAX INTEGER {
        true(1),
        false(2)
    }
    ACCESS read-write
    STATUS mandatory
    DESCRIPTION
        "If true(1), the PING time out value will be
        used to time out dynamic addresses."
    ::= { macip 7 }

macipIdleTimeOut OBJECT-TYPE
    SYNTAX INTEGER
    ACCESS read-write
    STATUS mandatory
    DESCRIPTION
        "Dynamic addresses will be made available to be
        reassigned after they have been idle for this
        length of time in minutes."
    ::= { macip 8 }

macipNBPConfirmTimeOut OBJECT-TYPE
    SYNTAX INTEGER
    ACCESS read-write
    STATUS mandatory
    DESCRIPTION
        "Dynamic addresses will be made available to be
        reassigned after they have not answered
        NBPConfirm for this length of time in minutes."
    ::= { macip 9 }

macipPINGTimeOut OBJECT-TYPE
    SYNTAX INTEGER
    ACCESS read-write
    STATUS mandatory
    DESCRIPTION
        "Dynamic addresses will be made available to be
        reassigned after they have not answered ICMP
        Echo (PING) for this length of time in
        minutes."
    ::= { macip 10 }

macipUseNetworkRestrictions OBJECT-TYPE
    SYNTAX INTEGER {
        true(1),
        false(2)
    }
    ACCESS read-write
    STATUS mandatory
    DESCRIPTION
        "If true(1), the network restrictions list will
        be used to restrict access to the gateway."
    ::= { macip 11 }


macipAddressesInUse OBJECT-TYPE
    SYNTAX INTEGER
    ACCESS read-only
    STATUS mandatory
    DESCRIPTION
        "The number of dynamic addresses that have been
        assigned."
    ::= { macip 12 }

macipNumClientsConnected OBJECT-TYPE
    SYNTAX INTEGER
    ACCESS read-only
    STATUS mandatory
    DESCRIPTION
        "The total number of clients (dynamic and
        static) that are currently using the gateway."
    ::= { macip 13 }

macipPacketsForwardedIP OBJECT-TYPE
    SYNTAX Counter
    ACCESS read-only
    STATUS mandatory
    DESCRIPTION
        "The number of packets forwarded to the IP
        internet. This number includes unknown IP
        errors."
    ::= { macip 14 }

macipPacketsForwardedAppleTalk OBJECT-TYPE
    SYNTAX Counter
    ACCESS read-only
    STATUS mandatory
    DESCRIPTION
        "The number of packets forwarded to the
        AppleTalk internet. This number includes
        unknown AppleTalk errors."
    ::= { macip 15 }

macipAssignRequestsRefusedErrs OBJECT-TYPE
    SYNTAX Counter
    ACCESS read-only
    STATUS mandatory
    DESCRIPTION
        "The number of times an attempt to get a
        dynamic address failed due to the address table
        being full."
    ::= { macip 16 }

macipInvalidIPAddressErrs OBJECT-TYPE
    SYNTAX Counter
    ACCESS read-only
    STATUS mandatory
    DESCRIPTION
        "The number of packets encountered from a
        client with an unknown or invalid IP address."
    ::= { macip 17 }

macipUnknownIPErrs OBJECT-TYPE
    SYNTAX Counter
    ACCESS read-only
    STATUS mandatory
    DESCRIPTION
        "The number of times the gateway failed to
        successfully forward an IP packet to the
        destination IP address."
    ::= { macip 18 }

macipUnknownAppleTalkErrs OBJECT-TYPE
    SYNTAX Counter
    ACCESS read-only
    STATUS mandatory
    DESCRIPTION
        "The number of times the gateway failed to
        successfully forward an IP packet to the
        destination AppleTalk address."
    ::= { macip 19 }

macipRunAtStartup OBJECT-TYPE
    SYNTAX INTEGER {
        true(1),
        false(2)
    }
    ACCESS read-write
    STATUS optional
    DESCRIPTION
        "If true(1), the gateway will run when the
        Macintosh starts up."
    ::= { macip 20 }

macipStatus OBJECT-TYPE
    SYNTAX INTEGER {
        enabled(1),
        disabled(2)
    }
    ACCESS read-only
    STATUS optional
    DESCRIPTION
        "The current status of the gateway."
    ::= { macip 21 }

macipNetRestrictionsTable OBJECT-TYPE
    SYNTAX SEQUENCE OF NetRestrictionsEntry
    ACCESS not-accessible
    STATUS optional
    DESCRIPTION
        "The list of networks being restricted from or
        allowed to use the gateway."
    ::= { macip 22 }

netRestrictionsEntry OBJECT-TYPE
    SYNTAX NetRestrictionsEntry
    ACCESS not-accessible
    STATUS optional
    DESCRIPTION
        "The description of one of the gateway's
        network restrictions."
    INDEX { netRestrictionsRangeStart }
    ::= { macipClientInfoTable 1 }

NetRestrictionsEntry ::= SEQUENCE {
    netRestrictionsRangeStart ATNetworkNumber,
    netRestrictionsRangeEnd ATNetworkNumber,
    netRestrictionsMode INTEGER
    }

netRestrictionsRangeStart OBJECT-TYPE
    SYNTAX ATNetworkNumber
    ACCESS read-write
    STATUS optional
    DESCRIPTION
        "The start of the range of networks to be
        restricted from using or allowed to use the
        gateway."
    ::= { netRestrictionsEntry 1 }

netRestrictionsRangeEnd OBJECT-TYPE
    SYNTAX ATNetworkNumber
    ACCESS read-write
    STATUS optional
    DESCRIPTION
        "The end of the range of networks to be
        restricted from using or allowed to use the
        gateway."
    ::= { netRestrictionsEntry 2 }

netRestrictionsMode OBJECT-TYPE
    SYNTAX INTEGER {
        allow(1),
        restrict(2)
    }
    ACCESS read-write
    STATUS optional
    DESCRIPTION
        "If allow(1), nodes on this network are allowed
        to use the gateway. If restrict(2), nodes on
        this network are restricted from using the
        gateway."
    ::= { netRestrictionsEntry 3 }

macipClientInfoTable OBJECT-TYPE
    SYNTAX SEQUENCE OF ClientInfoEntry
    ACCESS not-accessible
    STATUS optional
    DESCRIPTION
        "The list of clients currently using this
        gateway."
    ::= { macip 23 }

clientInfoEntry OBJECT-TYPE
    SYNTAX ClientInfoEntry
    ACCESS not-accessible
    STATUS optional
    DESCRIPTION
        "The description of one of the clients using
        this gateway."
    INDEX { dynamicAddrIPAddr }
    ::= { macipClientInfoTable 1 }

ClientInfoEntry ::= SEQUENCE {
    clientInfoIPAddr IpAddress,
    clientInfoAppleTalkAddr DdpNodeAddress,
    clientInfoOwnerName OCTET STRING,
    clientInfoPacketsForwarded Counter,
    clientInfoIdleTime INTEGER
}

clientInfoIPAddr OBJECT-TYPE
    SYNTAX IpAddress
    ACCESS read-only
    STATUS optional
    DESCRIPTION
        "The IP address assigned to the client."
    ::= { clientInfoEntry 1 }

clientInfoAppleTalkAddr OBJECT-TYPE
    SYNTAX DdpNodeAddress
    ACCESS read-only
    STATUS optional
    DESCRIPTION
        "The AppleTalk address of the client."
    ::= { clientInfoEntry 2 }

clientInfoOwnerName OBJECT-TYPE
    SYNTAX OCTET STRING
    ACCESS read-only
    STATUS optional
    DESCRIPTION
        "The client's owner name."
    ::= { clientInfoEntry 3 }

clientInfoPacketsForwarded OBJECT-TYPE
    SYNTAX Counter
    ACCESS read-only
    STATUS optional
    DESCRIPTION
        "The number of packets forward to the IP
        internet for this client plus the number of
        packets forwarded to the client."
    ::= { clientInfoEntry 4 }

clientInfoIdleTime OBJECT-TYPE
    SYNTAX INTEGER
    ACCESS read-only
    STATUS optional
    DESCRIPTION
        "The length of time in seconds that the client
        has been idle."
    ::= { clientInfoEntry 5 }

END
