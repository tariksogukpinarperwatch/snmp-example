-- **********************************************************************
-- **********************************************************************
-- This is the 3Com ECS branch of the 3Com enterprise MIB.
--
-- This MIB is specifically For the HubMan II products.
-- 
-- MIB Version:         MSH 2.3 (non generic bits only)
--
-- Comments:            
-- ECS Specific Branch. Objects from here do not form part of the
-- generic chassis MIB. 
--
-- History:             Date                    Reason for Change
--                      22 Mar 95               Created - Inconsistencies
--                                              amended to use smic tool.
--
-- **********************************************************************
--	Copyright 3Com Technologies Limited. (1991-1995)
-- **********************************************************************


-- ecsV23 { iso org(3) dod(6) internet(1) mgmt(2) 2 }

-- --------------------------------------------------------------------
-- ************ THE STARTING POINT FOR ALL MIB DEFINITIONS ************
-- --------------------------------------------------------------------

          LBHUB-ECS-MIB DEFINITIONS ::= BEGIN

          IMPORTS
                  mgmt, NetworkAddress, IpAddress, Counter, Gauge,
                          TimeTicks, enterprises
                      FROM RFC1155-SMI
                  OBJECT-TYPE
		      FROM RFC-1212
		  TRAP-TYPE
		      FROM RFC-1215
		  DisplayString, PhysAddress -- , snmp, ifIndex
		      FROM RFC1213-MIB;

          --  This MIB module uses the extended OBJECT-TYPE macro as
          --  defined in RFC 1212;

          --  MIB-II (same prefix as MIB-I)

          mib-2      OBJECT IDENTIFIER ::= { mgmt 1 }

          -- textual conventions

          DisplayString ::= OCTET STRING
          -- This data type is used to model textual information taken
          -- from the NVT ASCII character set.  By convention, objects
          -- with this syntax are declared as having
          --
          --      SIZE (0..255)

          PhysAddress ::= OCTET STRING
          -- This data type is used to model media addresses.  For many
          -- types of media, this will be in a binary representation.
          -- For example, an ethernet address would be represented as
          -- a string of 6 octets.

          -- groups in MIB-II

          system       OBJECT IDENTIFIER ::= { mib-2 1 }
          interfaces   OBJECT IDENTIFIER ::= { mib-2 2 }
          at           OBJECT IDENTIFIER ::= { mib-2 3 }
          ip           OBJECT IDENTIFIER ::= { mib-2 4 }
          icmp         OBJECT IDENTIFIER ::= { mib-2 5 }
          tcp          OBJECT IDENTIFIER ::= { mib-2 6 }
          udp          OBJECT IDENTIFIER ::= { mib-2 7 }
          egp          OBJECT IDENTIFIER ::= { mib-2 8 }

          -- historical (some say hysterical)
          -- cmot      OBJECT IDENTIFIER ::= { mib-2 9 }
          transmission OBJECT IDENTIFIER ::= { mib-2 10 }
          snmp         OBJECT IDENTIFIER ::= { mib-2 11 }


-- --------------------------------------------------------------------
-- ******************* PRIVATE BRANCH FOR 3Com ************************
-- --------------------------------------------------------------------

-- private		OBJECT IDENTIFIER ::= { internet 4 }
-- enterprises	OBJECT IDENTIFIER ::= { private 1 }

a3Com		OBJECT IDENTIFIER ::= { enterprises 43 }

products	OBJECT IDENTIFIER ::= { a3Com 1 }

	terminalServer		OBJECT IDENTIFIER ::= { products 1 }
	dedicatedBridgeServer	OBJECT IDENTIFIER ::= { products 2 }
	dedicatedRouteServer	OBJECT IDENTIFIER ::= { products 3 }
	brouter			OBJECT IDENTIFIER ::= { products 4 }
	genericMSWorkstation	OBJECT IDENTIFIER ::= { products 5 }
	genericMSServer		OBJECT IDENTIFIER ::= { products 6 }
	genericUnixServer	OBJECT IDENTIFIER ::= { products 7 }
	hub			OBJECT IDENTIFIER ::= { products 8 }
	cards			OBJECT IDENTIFIER ::= { products 9 }

		linkBuilder3GH		OBJECT IDENTIFIER ::= { hub 1 }
		linkBuilder10BTi	OBJECT IDENTIFIER ::= { hub 2 }
		linkBuilderECS		OBJECT IDENTIFIER ::= { hub 3 }
		linkBuilderMSH		OBJECT IDENTIFIER ::= { hub 4 }
		linkBuilderFMS		OBJECT IDENTIFIER ::= { hub 5 }
		linkBuilderFMSLBridge	OBJECT IDENTIFIER ::= { hub 10 }
		linkBuilderFMSII	OBJECT IDENTIFIER ::= { hub 7 }

		linkBuilder3GH-cards	OBJECT IDENTIFIER ::= { cards 1 }
		linkBuilder10BTi-cards	OBJECT IDENTIFIER ::= { cards 2 }
		linkBuilderECS-cards	OBJECT IDENTIFIER ::= { cards 3 }
		linkBuilderMSH-cards	OBJECT IDENTIFIER ::= { cards 4 }
		linkBuilderFMS-cards	OBJECT IDENTIFIER ::= { cards 5 }
		linkBuilderFMSII-cards	OBJECT IDENTIFIER ::= { cards 6 }

			linkBuilder10BTi-cards-utp	OBJECT IDENTIFIER ::= { linkBuilder10BTi-cards 1 }
			linkBuilder10BT-cards-utp	OBJECT IDENTIFIER ::= { linkBuilder10BTi-cards 2 }

			linkBuilderFMS-cards-utp	OBJECT IDENTIFIER ::= { linkBuilderFMS-cards 1 }
			linkBuilderFMS-cards-coax	OBJECT IDENTIFIER ::= { linkBuilderFMS-cards 2 }
			linkBuilderFMS-cards-fiber	OBJECT IDENTIFIER ::= { linkBuilderFMS-cards 3 }
			linkBuilderFMS-cards-12fiber	OBJECT IDENTIFIER ::= { linkBuilderFMS-cards 4 }
			linkBuilderFMS-cards-24utp	OBJECT IDENTIFIER ::= { linkBuilderFMS-cards 5 }

			linkBuilderFMSII-cards-12tp-rj45	OBJECT IDENTIFIER ::= { linkBuilderFMSII-cards 1 }
			linkBuilderFMSII-cards-10coax-bnc	OBJECT IDENTIFIER ::= { linkBuilderFMSII-cards 2 }
			linkBuilderFMSII-cards-6fiber-st	OBJECT IDENTIFIER ::= { linkBuilderFMSII-cards 3 }
			linkBuilderFMSII-cards-12fiber-st	OBJECT IDENTIFIER ::= { linkBuilderFMSII-cards 4 }
			linkBuilderFMSII-cards-24tp-rj45	OBJECT IDENTIFIER ::= { linkBuilderFMSII-cards 5 }
			linkBuilderFMSII-cards-24tp-telco	OBJECT IDENTIFIER ::= { linkBuilderFMSII-cards 6 }

--experimental		OBJECT IDENTIFIER ::= { a3Com 2 }
amp-mib			OBJECT IDENTIFIER ::= { a3Com 3 }
genericTrap		OBJECT IDENTIFIER ::= { a3Com 4 }
viewBuilderApps		OBJECT IDENTIFIER ::= { a3Com 5 }
specificTrap		OBJECT IDENTIFIER ::= { a3Com 6 }
linkBuilder3GH-mib	OBJECT IDENTIFIER ::= { a3Com 7 }
linkBuilder10BTi-mib 	OBJECT IDENTIFIER ::= { a3Com 8 }
linkBuilderECS-mib	OBJECT IDENTIFIER ::= { a3Com 9 }
generic			OBJECT IDENTIFIER ::= { a3Com 10 }

        genExperimental 	OBJECT IDENTIFIER ::= { generic 1 }
	setup			OBJECT IDENTIFIER ::= { generic 2 }
	sysLoader		OBJECT IDENTIFIER ::= { generic 3 }
	security		OBJECT IDENTIFIER ::= { generic 4 }
	gauges			OBJECT IDENTIFIER ::= { generic 5 }
	asciiAgent		OBJECT IDENTIFIER ::= { generic 6 }
	serialIf		OBJECT IDENTIFIER ::= { generic 7 }
	repeaterMgmt		OBJECT IDENTIFIER ::= { generic 8 }
	endStation		OBJECT IDENTIFIER ::= { generic 9 }
	localSnmp		OBJECT IDENTIFIER ::= { generic 10 }
	manager			OBJECT IDENTIFIER ::= { generic 11 }
	unusedGeneric12		OBJECT IDENTIFIER ::= { generic 12 }
	chassis			OBJECT IDENTIFIER ::= { generic 14 }
	mrmResilience		OBJECT IDENTIFIER ::= { generic 15 }
	tokenRing		OBJECT IDENTIFIER ::= { generic 16 }
	multiRepeater 		OBJECT IDENTIFIER ::= { generic 17 }
	bridgeMgmt		OBJECT IDENTIFIER ::= { generic 18 }
	fault			OBJECT IDENTIFIER ::= { generic 19 }
	poll			OBJECT IDENTIFIER ::= { generic 20 }
	powerSupply		OBJECT IDENTIFIER ::= { generic 21 }

		testData	OBJECT IDENTIFIER ::= { genExperimental 1 }
		ifExtensions	OBJECT IDENTIFIER ::= { genExperimental 2 }

netBuilder-mib		OBJECT IDENTIFIER ::= { a3Com 11 }
lBridgeECS-mib		OBJECT IDENTIFIER ::= { a3Com 12 }
deskMan-mib		OBJECT IDENTIFIER ::= { a3Com 13 }
linkBuilderMSH-mib	OBJECT IDENTIFIER ::= { a3Com 14 }


	ecsAgent                	OBJECT IDENTIFIER ::= { linkBuilderECS-mib 1 }
   ecsEnvironment          	OBJECT IDENTIFIER ::= { linkBuilderECS-mib 2 }
   ecsRLCResilientLinks       OBJECT IDENTIFIER ::= { linkBuilderECS-mib 3 }
   ecsSecureRepeaterLineCards OBJECT IDENTIFIER ::= { linkBuilderECS-mib 4 }
   ecsRepeaterLineCard     	OBJECT IDENTIFIER ::= { linkBuilderECS-mib 5 }
   ecsRLCStationLocate        OBJECT IDENTIFIER ::= { linkBuilderECS-mib 6 }      
   ecsHubStatistics    	      OBJECT IDENTIFIER ::= { linkBuilderECS-mib 8 }      
   ecsVideo    		         OBJECT IDENTIFIER ::= { linkBuilderECS-mib 9 }      


   lbecsXENDOFMIB			OBJECT IDENTIFIER ::= { linkBuilderECS-mib 255 }


-- Object Definitions


-- 5. Ether Connect System Definitions

-- The name of the port p is the OBJECT IDENTIFIER value of the form a.b, such 
-- that a.b is the value of that instance of the port associated with p.
-- For each object type t for which the defined name n has a prefix of 
-- ECSPortEntry, an instance i of t is named by an object identifier of the 
-- form n.p.s where p.s is the name of the port and slot about which i 
-- represents information. 

-- For example, suppose one wanted to identify an instance of the variable
-- GoodRcvdFrames associated with slot 1, port 3.  Accordingly, 
-- GoodRcvdFrames.3.1 would identitify the desired instance.


--  BDN/ECS SPECIFIC GROUPS FOR THE AGENT

-- The ecsAgent Group (ecs 1)
                          
--    	       ecsAgentSystemIdentifier OBJECT-TYPE
--    	               SYNTAX ECSAgentSystemIdentifier
--    	               ACCESS read-only
--                       STATUS deprecated
-- 		       DESCRIPTION
-- 		       "Identifies the type, version and capabilities
--                       of the system."
--                       ::=  { ecsAgent 1 } 
--
--    	       ECSAgentSystemIdentifier ::= SEQUENCE {
--		       ecsManufacturerId
--			  DisplayString (SIZE (0..32)),
--		       ecsManufacturerProductId
--			  DisplayString (SIZE (0..32)),
--		       ecsSoftwareVersionNumber
--			  DisplayString (SIZE (0..16)),
--		       ecsHardwareVersionNumber
--			  INTEGER (1..255)
--	         }
--
     	       ecsAgentSystemIdentifier OBJECT IDENTIFIER ::=  { ecsAgent 1 } 

               ecsManufacturerId OBJECT-TYPE
                       SYNTAX DisplayString (SIZE (0..32))
                       ACCESS read-only
                       STATUS deprecated
 		       DESCRIPTION
 		       "An atrribute to identify the manufacturer"
                       ::=  { ecsAgentSystemIdentifier 1 } 

               ecsManufacturerProductId OBJECT-TYPE
                       SYNTAX DisplayString (SIZE (0..32))
                       ACCESS read-only
                       STATUS mandatory
 		       DESCRIPTION
 		       "An attribute to identify the product id."
                       ::=  { ecsAgentSystemIdentifier 2 } 

               ecsSoftwareVersionNumber OBJECT-TYPE
                       SYNTAX DisplayString (SIZE (0..16))
                       ACCESS read-only
                       STATUS deprecated
 		       DESCRIPTION
 		       "An atrribute to identify the software version."
                       ::=  { ecsAgentSystemIdentifier 3 } 

               ecsHardwareVersionNumber OBJECT-TYPE
                       SYNTAX INTEGER
                       ACCESS read-only
                       STATUS deprecated
 		       DESCRIPTION
 		       "An atrribute to identify the hardware version."
                       ::=  { ecsAgentSystemIdentifier 4 } 

               ecsAgentSystemName OBJECT-TYPE
                       SYNTAX DisplayString (SIZE (32))
                       ACCESS read-write
                       STATUS deprecated
 		       DESCRIPTION
 		       "This is an informational string that could be used to show
                       the name of the ECSAgent or management agent."
                       ::=   { ecsAgent 2 }  

               ecsAgentSystemLocation OBJECT-TYPE
                       SYNTAX DisplayString (SIZE (32))
                       ACCESS read-write
                       STATUS deprecated
                       DESCRIPTION
                       "This is an informational string that could be used to show
                       the  physical location (i.e., area) of the ecsAgent
                       or management agent."
                       ::=   { ecsAgent 3 }
 
               ecsAgentSystemTime OBJECT-TYPE
                       SYNTAX 	TimeTicks
                       ACCESS read-write
                       STATUS deprecated
 		       DESCRIPTION
 		       "A representation of the system time of the management
                        system, taken from the epoch."
                       ::=  {  ecsAgent 4 }
  
               ecsAgentStatus OBJECT-TYPE
                       SYNTAX INTEGER {
                                  offline(1),    -- the ecsAgent is off line  
                                  online(2)      -- the ecsAgent is on line  
	   	              }
                       ACCESS read-only
                       STATUS mandatory
 		       DESCRIPTION
 		       "Indicates that the management agent is on line and operating."   
                       ::=  { ecsAgent 5 }  

               ecsAgentAuthenticationStatus OBJECT-TYPE
                       SYNTAX INTEGER {
                                   enabled(1),  -- the address checking of management frames enabled  
                                   disabled(2)    -- the address checking of management frames off
	   	              }
                       ACCESS read-only
                       STATUS mandatory
 		       DESCRIPTION
 		       "Indicates whether management frames are checked against entries
 			in the management tranmiter table."   
                       ::=  { ecsAgent 6 } 

               ecsAgentSecureManagementStatus OBJECT-TYPE
                       SYNTAX INTEGER {
                                   enabled(1),  -- the secure man allowed  
                                   disabled(2),   -- the secure management not allowed
				   secure-menu-entered(3), -- secure menus entered
				   secure-password-violation(4),
				   secure-config-update(5)
	   	              }
                       ACCESS read-only
                       STATUS mandatory
 		       DESCRIPTION
 		       "Indicates whether the remote management of the security features
 			of the ECS are enabled or not."   
                       ::=  { ecsAgent 7 }  

               ecsAgentFrontPanelSetupPassword OBJECT-TYPE
                       SYNTAX 		DisplayString (SIZE (0..8))
                       ACCESS read-write
                       STATUS mandatory
 		       DESCRIPTION
 		       "The password used to gain access to the configuration 
 			features of the front panel control of the device."
                       ::=  {  ecsAgent  11 }

               ecsAgentFrontPanelDisplay OBJECT-TYPE
                       SYNTAX 		DisplayString (SIZE (0..24))
                       ACCESS read-write
                       STATUS mandatory
 		       DESCRIPTION
 		       "The string displayed on the front panel." 
                       ::=  {  ecsAgent 12 }

               ecsAgentFrontPanelPassword OBJECT-TYPE
                       SYNTAX 		DisplayString (SIZE (0..8))
                       ACCESS read-write
                       STATUS mandatory
 		       DESCRIPTION
 		       "The password used to gain access to the front panel control
                       of the device."
                       ::=  {  ecsAgent  13 }

               ecsAgentFrontPanelSecurePassword OBJECT-TYPE
                       SYNTAX 		DisplayString (SIZE (0..8))
                       ACCESS read-write
                       STATUS mandatory
 		       DESCRIPTION
 		       "The password used to gain access to the security 	
 			features of the front panel control
                       of the device. This attribute is not viewable until
 			secure remote management is enabled."
                       ::=  {  ecsAgent  14 }

               ecsAgentFrontPanelLock OBJECT-TYPE
                       SYNTAX INTEGER {
			                off(1), -- Station front panel is unlocked.
			                on(2)	-- Station front panel is not locked.
		              }
                       ACCESS read-write
                       STATUS mandatory
 		       DESCRIPTION
 		       "The station front panel status." 
                       ::=  { ecsAgent  15 }


               ecsAgentResetDevice OBJECT-TYPE
                       SYNTAX INTEGER {
			                 notreset(1),	-- not resetting  
			                 reset(2)	-- resetting  
		              }
                       ACCESS read-write
                       STATUS mandatory
 		       DESCRIPTION
 		       "Network management module reset status. Writing a 2 to this
                       object will reset the management agent." 
                       ::=  { ecsAgent 16 }

               ecsAgentRestart OBJECT-TYPE
                       SYNTAX INTEGER {
			                notrestart(1),		-- not restarting  
			                restart(2)		-- restarting  
		              }
                       ACCESS read-write
                       STATUS mandatory
 		       DESCRIPTION
 		       "Network management module restart status. Writing a 2 to his 
                       object will restart the management agent. This initializes all
                       the counters, rereads the NVRAM data structure, and starts
                       executing from the beginning of the code." 
                       ::=  { ecsAgent 18 }

               ecsAgentDefaultConfig OBJECT-TYPE
                       SYNTAX INTEGER {
			                normal(1),		-- not reverting to original 
						                -- configuration  
			                reverting(2)		-- reverting to orig config  
		             }
                       ACCESS read-write
                       STATUS mandatory
 		       DESCRIPTION
 		       "The device is returned to its factory settings." 
                       ::=  { ecsAgent 19 }



-- ecsAgentManagementTable Object Type Names
                    
                    
-- The name of the management address x is the OBJECT IDENTIFIER value of the form
-- the form n.y where y is the name of the trapreceviver address about which i 
-- represents information.


               ecsAgentManagementTable OBJECT-TYPE
                       SYNTAX SEQUENCE OF ECSAgentManagementEntry
                       ACCESS not-accessible
                       STATUS mandatory
 		       DESCRIPTION
 		       "This entity's management address table. (10 entries)" 
                       ::=  { ecsAgent 20 }

               ecsAgentManagementEntry OBJECT-TYPE
                       SYNTAX ECSAgentManagementEntry
                       ACCESS not-accessible
                       STATUS mandatory
 		       DESCRIPTION
 		       " A source address address and privileges of a particular
                       management station."
                       INDEX   { ecsAgentManagementAddr } 
                       ::=   { ecsAgentManagementTable 1 }
		
               ECSAgentManagementEntry ::= SEQUENCE {
		       ecsAgentManagementAddr  
			  IpAddress,  
		       ecsAgentManagementAccess  
		          INTEGER,  
		       ecsAgentManAccessLevel  
		          INTEGER 
	       }


               ecsAgentManagementAddr OBJECT-TYPE
                       SYNTAX 	IpAddress
                       ACCESS read-write
                       STATUS mandatory
 		       DESCRIPTION
 		       "IpAddress of the management station. " 
                       ::=  { ecsAgentManagementEntry 1 }

               ecsAgentManagementAccess OBJECT-TYPE
                       SYNTAX INTEGER {
					invalid(1),	-- entry is deleted
			                off(2),		-- entry is valid but disabled 
					superread(3),	-- allowed to view ecsAgent group table 
					superreadwrite(4),	-- allowed to view and change ecsAgent group table 
			                readonly(5),	-- only read requests (GET) will be accepted 
					readwrite(6),	-- read (GET) and (SET) requests accepted
					readonlysecure(7),	-- read (GET) requests accepted
					readwritesecure(8)	-- read (GET) and (SET) requests accepted
		              }
                       ACCESS read-write -- actually write-only
                       STATUS mandatory
 		       DESCRIPTION
 		       "Setting this object to the value invalid(1) invalidates the
                       corresponding entry in the   ecsAgentManagementTable.
                       That is, it effectively disassociates the address
                       identified with the entry by removing the entry from the table."
                       ::=   { ecsAgentManagementEntry 2 }

               ecsAgentManAccessLevel OBJECT-TYPE
                       SYNTAX INTEGER 
                       ACCESS read-write
                       STATUS mandatory
 		       DESCRIPTION
 		       "The level of aceess attributed to tthis entry in the table."
                       ::=   { ecsAgentManagementEntry 3 }

-- ecsAgentTrapReceiverTable Object Type Names


               ecsAgentTrapReceiverTable OBJECT-TYPE
                       SYNTAX SEQUENCE OF ECSAgentTrapReceiverEntry
                       ACCESS not-accessible
                       STATUS mandatory
 		       DESCRIPTION
 		       "This entity's Trap Receiver Table. (10 entries)" 
                       ::=  { ecsAgent 21 }

               ecsAgentTrapReceiverEntry OBJECT-TYPE
                       SYNTAX ECSAgentTrapReceiverEntry
                       ACCESS not-accessible
                       STATUS mandatory
 		       DESCRIPTION
 		       " A destination address and community string for a particular
                       trap receiver."
                       INDEX   { ecsAgentTrapReceiverAddr } 
                       ::=   { ecsAgentTrapReceiverTable 1 }
		
               ECSAgentTrapReceiverEntry ::= SEQUENCE {
		       ecsAgentTrapReceiverAddr  
			  IpAddress,  
		       ecsAgentTrapType  
		          INTEGER,  
		       ecsAgentTrapReceiverComm  
		          DisplayString (SIZE(0..20)),
		       ecsAgentTrapLevel 
			  INTEGER 
	       }


               ecsAgentTrapReceiverAddr OBJECT-TYPE
                       SYNTAX 		IpAddress
                       ACCESS read-write
                       STATUS mandatory
 		       DESCRIPTION
 		       "IpAddress for trap receiver." 
                       ::=  { ecsAgentTrapReceiverEntry 1 }

               ecsAgentTrapType OBJECT-TYPE
                       SYNTAX INTEGER {
					invalid(1),	-- entry is deleted
			                off-on(2),	-- traps will not be sent to this address  
			                generic(3),	
					psu(4),
					fanfail(5),
					configuractionchange(6),
					port(7),
					resilience(8),
					rate(9),
					stationlocate(10),
					secure(11),
					secureport(12)
		       }
                       ACCESS read-write -- actually write-only
                       STATUS mandatory
 		       DESCRIPTION
 		       "Setting this object to the value invalid(1) invalidates the
                       corresponding entry in the   ECSAgentTrapReceiverTable.
                       That is, it effectively disassociates the address
                       identified with the entry by removing the entry from the table."
                       ::=   { ecsAgentTrapReceiverEntry 2 }

               ecsAgentTrapReceiverComm OBJECT-TYPE
                       SYNTAX 		DisplayString (SIZE (0..20))
                       ACCESS read-write
                       STATUS mandatory
 		       DESCRIPTION
 		       "Community string used for traps." 
                       ::=  { ecsAgentTrapReceiverEntry 3 }

               ecsAgentTrapLevel OBJECT-TYPE
                       SYNTAX INTEGER
                       ACCESS read-only
                       STATUS mandatory
 		       DESCRIPTION
 		       "Indicates the type of traps that will be sent to this 
 			address."
                       ::=   { ecsAgentTrapReceiverEntry 4 }



               ecsAgentAuthTrapState OBJECT-TYPE
                       SYNTAX INTEGER {
			                enable(1),	-- disable authentication traps  
			                disable(2)	-- enable authentication traps  
		              }
                       ACCESS read-write
                       STATUS deprecated
 		       DESCRIPTION
 		       "Enable or disable the use of authentication error trap generation."
                       ::=  { ecsAgent 22 }

               ecsAgentIpAddr OBJECT-TYPE
                       SYNTAX IpAddress
                       ACCESS read-write
                       STATUS mandatory
 		       DESCRIPTION
 		       "The network management module's administrative IpAddress. The
                       current operational IpAddress can be obtained from the
                       ipAdEntAddr entry in the ipAddrTable." 
                       ::=  { ecsAgent 23 }

               ecsAgentIpNetmask OBJECT-TYPE
                       SYNTAX IpAddress
                       ACCESS read-write
                       STATUS mandatory
 		       DESCRIPTION
 		       "The network management module's administrative subnet mask.
                       The current operational subnet mask can be obtained from
                       the ipAdEntNetMask entry in the ipAddrTable." 
                       ::=  { ecsAgent 24 }

               ecsAgentDefaultGateway OBJECT-TYPE
                       SYNTAX IpAddress
                       ACCESS read-write
                       STATUS mandatory
 		       DESCRIPTION
 		       "The network management module's administrative default
                       gateway IpAddress. The current operational default
                       gateway's IpAddress can be obtained from the ipRoutingTable." 
                       ::=  { ecsAgent 25 }

               ecsAgentIpBroadAddr OBJECT-TYPE
                       SYNTAX IpAddress
                       ACCESS read-write
                       STATUS mandatory
 		       DESCRIPTION
 		       "The network management module's adminstrative default
                       broadcast address" 
                       ::=  { ecsAgent 26 }

               ecsAgentMACAddress OBJECT-TYPE
                       SYNTAX OCTET STRING
                       ACCESS read-only
                       STATUS mandatory
 		       DESCRIPTION
 		       "The  MAC address of the ECS Agent." 
                       ::=  { ecsAgent 27 }  

               ecsAgentSecureTrapState OBJECT-TYPE
                       SYNTAX INTEGER {
			        enable(1),	-- disable security traps  
			        disable(2)	-- enable security traps  
		       }
                       ACCESS read-write
                       STATUS mandatory
 		       DESCRIPTION
 		       "Enable or disable the generation of security traps."
                       ::=  { ecsAgent 28 }

               ecsAgentLastSystemError OBJECT-TYPE
                       SYNTAX INTEGER
                       ACCESS read-only
                       STATUS mandatory
 		       DESCRIPTION
 		       "The error number of the last system error."
                       ::=  { ecsAgent 29 }

               ecsAgentLastTrap OBJECT-TYPE
                       SYNTAX TimeTicks
                       ACCESS read-only
                       STATUS mandatory
 		       DESCRIPTION
 		       "The time, taken from the epoch when the last trap
 			or event would have been generated."
                       ::=  { ecsAgent 30 }


--      ENVIRONMENT GROUP
 
-- Elements of the tables defined in this group are indexed (object instance)
-- by slot.  The object instance is concatenated to the object identifier.

 	       ecsRackType OBJECT-TYPE
		       SYNTAX INTEGER {
				unknown(1),
				ecs4(2),
				ecs10(3)
		       }
		       ACCESS read-only
		       STATUS mandatory
 		       DESCRIPTION
 		       "The rack type of the LinkBuilder ECS."
		       ::= {ecsEnvironment 1}


               ecsRackConfigurationTable OBJECT-TYPE
                       SYNTAX SEQUENCE OF ECSSlotConfigEntry
                       ACCESS not-accessible
		       STATUS mandatory
 		       DESCRIPTION
 		       "The current configuration of the Ether Connect System 
 			rack." 
                       ::=  {ecsEnvironment 2}


               ecsSlotConfigEntry OBJECT-TYPE
                       SYNTAX ECSSlotConfigEntry
                       ACCESS not-accessible
                       STATUS mandatory
 		       DESCRIPTION
 		       "The description of the type of module in each slot."
                       INDEX   {  ecsSlotConfigIndex }
                       ::=  { ecsRackConfigurationTable 1}

               ECSSlotConfigEntry ::= SEQUENCE {
		       ecsSlotConfigIndex
			  INTEGER,
		       ecsSlotCardName
			  DisplayString, 
                       ecsSlotDeviceType
                          INTEGER,
                       ecsSlotSoftVerNum
                          DisplayString,
                       ecsSlotHardVerNum
                          INTEGER,
                       ecsSlotNumOfPorts
                          INTEGER,
                       ecsSlotMediaType
                          DisplayString,
                       ecsCardReset
                          INTEGER,
                       ecsLampOverRide
                	  INTEGER,
		       ecsCardIsolated
			  INTEGER,
		       ecsCardIpAddress
			  IpAddress
                }
   
                ecsSlotConfigIndex OBJECT-TYPE
                       SYNTAX INTEGER
                       ACCESS read-only
                       STATUS mandatory
 		       DESCRIPTION
 		       "The device type found in a slot." 
                       ::=  { ecsSlotConfigEntry 1 }
             
               ecsSlotCardName OBJECT-TYPE
                       SYNTAX DisplayString (SIZE (0..16))
                       ACCESS read-write
                       STATUS mandatory
 		       DESCRIPTION
 		       "This is an informational string that could be 
                       used to show the name of a card."
                       ::=   { ecsSlotConfigEntry 2 }  

                ecsSlotDeviceType OBJECT-TYPE
                        SYNTAX INTEGER {
                                          empty(1),
					  unknown(2),	-- None of the following
                                          managementcard(3),
                                          thinEthernetCard(4),
                                          thinEthernetCardpAUI(5),
                                          unshieldedTwistedPair(6),
                                          fibre(7),
                                          bridge-Line-Card(8),
                                          monitor(9),
					  shieldedTwistedPair(10),
					  fanout(11),
					  secureUnshieldedTP(12),
					  secureSheildedTP(13),
					  secureFibre(14),
					  secureFanout(15),
					  secureThinEthernet(16),
					  terminalserver(17),
					  remotebridge(18),
					  videoswitch(19)
                               }
                       ACCESS read-only
                       STATUS mandatory
 		       DESCRIPTION
 		       "The device type found in a slot." 
                       ::=  { ecsSlotConfigEntry 3 }
 
               ecsSlotSoftVerNum OBJECT-TYPE
                       SYNTAX DisplayString (SIZE(0..16))
                       ACCESS read-only
                       STATUS mandatory
 		       DESCRIPTION
 		       "A description of the software version number." 
                       ::=  { ecsSlotConfigEntry 4 }
 
               ecsSlotHardVerNum OBJECT-TYPE
                       SYNTAX INTEGER
                       ACCESS read-only
                       STATUS mandatory
 		       DESCRIPTION
 		       "Hardware version number of the card." 
                       ::=  { ecsSlotConfigEntry 5 }
 
               ecsSlotNumOfPorts OBJECT-TYPE
                       SYNTAX INTEGER
                       ACCESS read-only
                       STATUS mandatory
 		       DESCRIPTION
 		       "The number of repeater ports on the card." 
                       ::=  { ecsSlotConfigEntry 6 }
 
               ecsSlotMediaType OBJECT-TYPE
                       SYNTAX DisplayString (SIZE (0..16))
                       ACCESS read-only
                       STATUS mandatory
 		       DESCRIPTION
 		       "The media type associated with this slot can take on the
                       following values: No port, AUI, Cheapernet, FOIRL, UTP, 
                       STP, FOASTAR, Through air, Plastic Fibre." 
                       ::=  { ecsSlotConfigEntry 7 }
 
               ecsCardReset OBJECT-TYPE
                       SYNTAX INTEGER {
                                        not-reset(1),       -- not reset
					reset(2)	    -- reset
                              }
                       ACCESS read-write
                       STATUS mandatory
 		       DESCRIPTION
 		       "The hardware for specified repeater line card is reset." 
                       ::=  { ecsSlotConfigEntry 8 }

               ecsLampOverRide OBJECT-TYPE
                       SYNTAX INTEGER {
			                 enabled(1), 	-- 	Lamps are forced enabled
			                 disabled(2)	-- 	Lamps are used normally. 
	  		      }
                       ACCESS read-write
                       STATUS mandatory
 		       DESCRIPTION
 		       "The lamps on the specified repeater line card are forced on for
                       normal operation." 
                       ::=  { ecsSlotConfigEntry 9 }


 
               ecsCardIsolated OBJECT-TYPE
                       SYNTAX INTEGER {
                                        not-isolated(1),
					isolated(2),
					cant-isolate(3)
                              }
                       ACCESS read-write
                       STATUS mandatory
 		       DESCRIPTION
 		       "The LinkBuilder ECS card is isolated from the chassis backplane." 
                       ::=  { ecsSlotConfigEntry 10 }

               ecsCardIpAddress OBJECT-TYPE
                       SYNTAX IpAddress
                       ACCESS read-only
                       STATUS mandatory
  		       DESCRIPTION
  		       "For some devices the LinkBuilder ECS may be able
 			to determine the IP address of a intelligent card
 			that is in the slot. If the value returned is
 			0.0.0.0 then this indicates that the address can
 			not be determined." 
                       ::=  { ecsSlotConfigEntry 11 }


 	       ecsPSUStatus OBJECT-TYPE
		       SYNTAX INTEGER {
				ok(1),
				psu1failed(2),
				psu2failed(3)
		       }
		       ACCESS read-only
		       STATUS mandatory
 		       DESCRIPTION
 		       "The status of the PSUs in the LinkBuilder ECS."
		       ::= {ecsEnvironment 3}

 	       ecsFanStatus OBJECT-TYPE
		       SYNTAX INTEGER {
				ok(1),
				failed(2)
		       }
		       ACCESS read-only
		       STATUS mandatory
 		       DESCRIPTION
 		       "The status of the fans in the LinkBuilder ECS."
		       ::= {ecsEnvironment 4}


 --  Resilient Links { ecs 3 }

               ecsRLCNumberOfResilientLinks OBJECT-TYPE
                       SYNTAX  INTEGER
                       ACCESS  read-only
                       STATUS  mandatory
 		       DESCRIPTION
 		       "The number of resilient links currently configured
 			on the LinkBuilder ECS."
                       ::= { ecsRLCResilientLinks 1 }

               ecsRLCNumberOfDOBPorts OBJECT-TYPE
                       SYNTAX  INTEGER
                       ACCESS  read-only
                       STATUS  mandatory
 		       DESCRIPTION
 		       "The total number of ports that are disabled on boot,
 			making them suitable for use with resilient links."
                       ::= { ecsRLCResilientLinks 2 }

-- Resilient Link Table 

               ecsRLCResilientLinkTable OBJECT-TYPE
                       SYNTAX  SEQUENCE OF ECSRLCResilientLinkEntry
                       ACCESS  not-accessible
                       STATUS  mandatory
DESCRIPTION ""
                       ::= { ecsRLCResilientLinks 3 }

               ecsRLCResilientLinkEntry OBJECT-TYPE
                       SYNTAX  ECSRLCResilientLinkEntry
                       ACCESS  not-accessible
                       STATUS  mandatory
DESCRIPTION ""
                       INDEX   { ecsRLMainLinkSlot, ecsRLMainLinkPort }  
                       ::= { ecsRLCResilientLinkTable 1 }

               ECSRLCResilientLinkEntry ::= SEQUENCE {
		       ecsRLMainLinkSlot
			  INTEGER,
		       ecsRLMainLinkPort
			  INTEGER,
		       ecsRLStandbySlot
			  INTEGER,
		       ecsRLStandbyPort
			  INTEGER,
		       ecsRLActiveLink
		          INTEGER,
		       ecsResLinkState
		          INTEGER	       
    		    }

 
               ecsRLMainLinkSlot OBJECT-TYPE
                       SYNTAX INTEGER
                       ACCESS read-write
                       STATUS mandatory
 		       DESCRIPTION
 		       "The Slot Number for the main link of this resilient link." 
                       ::=  { ecsRLCResilientLinkEntry 1 }

               ecsRLMainLinkPort OBJECT-TYPE
                       SYNTAX INTEGER
                       ACCESS read-write
                       STATUS mandatory
 		       DESCRIPTION
 		       "The Port Number for the main link of this resilient link." 
                       ::=  { ecsRLCResilientLinkEntry 2 }

 
               ecsRLStandbySlot OBJECT-TYPE
                       SYNTAX INTEGER
                       ACCESS read-write
                       STATUS mandatory
 		       DESCRIPTION
 		       "The Slot Number for the standby link of this resilient link." 
                       ::=  { ecsRLCResilientLinkEntry 3 }

               ecsRLStandbyPort OBJECT-TYPE
                       SYNTAX INTEGER
                       ACCESS read-write
                       STATUS mandatory
 		       DESCRIPTION
 		       "The Port Number for the standby link of this resilient link." 
                       ::=  { ecsRLCResilientLinkEntry 4 }

               ecsRLActiveLink OBJECT-TYPE
                       SYNTAX INTEGER {
				unknown(1),
				none(2),
				main(3),
				standby(4),
				both(5)
		       }
                       ACCESS read-only
                       STATUS mandatory
 		       DESCRIPTION
 		       "The resilient link currently in use for traffic transmission. For
 			a read the attribute indicates which link is active. 
 			A new link will always be configured with the main
 			link being the active link. If the link status cannot be determined,
 			the value unknown(1) is returned." 
                       ::=  { ecsRLCResilientLinkEntry 5 }


               ecsResLinkState OBJECT-TYPE
                      SYNTAX INTEGER {
				invalid(1),
				operational(2),
				non-operational(3),
				switchlink(4),
				standby-jumperfault(5),
				main-absent(6),
				standby-absent(7),
				main-failed(8),
				standby-failed(9),
				both-failed(10)				
		       }
                       ACCESS read-write
                       STATUS mandatory
DESCRIPTION ""
                       ::=  { ecsRLCResilientLinkEntry 6 }


-- ecsSecureRepeaterLineCards { ecs 4 }

               ecsSecureRLCMode OBJECT-TYPE
                       SYNTAX INTEGER {
				on(1), 	-- The secure management is enabled
				off(2)	-- Secure management disabled
			}
                       ACCESS read-only
                       STATUS mandatory
 		       DESCRIPTION
 		       "Determines whether the management of Secure
 			Repeater Line Cards is disabled or not." 
                       ::=  { ecsSecureRepeaterLineCards 1 }

               ecsSecureTrapRepRate OBJECT-TYPE
                       SYNTAX INTEGER {
				continuous(1),
				one-minute(2),
			        fifteen-mins(3),
			        sixty-minutes(4)
		       }
                       ACCESS read-write
                       STATUS mandatory
 		       DESCRIPTION
 		       "Determines the rate at which secure traps are sent
 			for a security violation." 
                       ::=  { ecsSecureRepeaterLineCards 2 }

               ecsSecureRLCTable OBJECT-TYPE
                       SYNTAX  SEQUENCE OF ECSSecureRLCEntry
                       ACCESS  not-accessible
                       STATUS  mandatory
 		       DESCRIPTION
 		       "A table which allows management
 			of the secure Repeater Line Cards." 
                       ::= { ecsSecureRepeaterLineCards 3 }

               ecsSecureRLCEntry OBJECT-TYPE
                       SYNTAX  ECSSecureRLCEntry
                       ACCESS  not-accessible
                       STATUS  mandatory
DESCRIPTION ""
                       INDEX   { ecsSecRLCSlotIndex, ecsSecRLCPortIndex } 
                       ::= { ecsSecureRLCTable 1 }

                ECSSecureRLCEntry ::= SEQUENCE {
		       ecsSecRLCSlotIndex    			
			  INTEGER,	
		       ecsSecRLCPortIndex    			
			  INTEGER,
		       ecsSecRLCLinkState
			  INTEGER,
		       ecsSecRLCPortState
			  INTEGER,
		       ecsSecRLCNTKState    			
			  INTEGER,	
		       ecsSecRLCBroadState
			  INTEGER,	
		       ecsSecRLCMultiState
			  INTEGER,
		       ecsSecRLCLearnMode
			  INTEGER,
		       ecsSecRLCReportMode
			  INTEGER,
		       ecsSecRLCMACAddress
			  OCTET STRING
		      }

               ecsSecRLCSlotIndex OBJECT-TYPE
                       SYNTAX INTEGER
                       ACCESS read-only
                       STATUS mandatory
 		       DESCRIPTION
 		       "The secure repeater line card slot index" 
                       ::=  { ecsSecureRLCEntry 1 }

               ecsSecRLCPortIndex OBJECT-TYPE
                       SYNTAX INTEGER
                       ACCESS read-only
                       STATUS mandatory
 		       DESCRIPTION
 		       "The secure repeater line card port index" 
                       ::=  { ecsSecureRLCEntry 2 }

               ecsSecRLCLinkState OBJECT-TYPE
                       SYNTAX INTEGER {
				other(1),
                                secure(2), -- Configured as a repeater
                                repeater(3)    -- Security is enabled 
                              }
                       ACCESS read-only
                       STATUS mandatory
 		       DESCRIPTION
 		       "Attribute to determine whether the security
 			features are enabled on this port of the secure Repeater Line Card." 
                       ::=  { ecsSecureRLCEntry 3 }

               ecsSecRLCPortState OBJECT-TYPE
                       SYNTAX INTEGER {
				other(1),
                                disabled(2),   -- Port is securely disabled
                                enabled(3),    -- Port is securely enabled
				unauthorised-station-seen(4),
				unauthorised-station-port-disabled(5),
				authorised-station-learnt(6)
                       }
                       ACCESS read-write
                       STATUS mandatory
 		       DESCRIPTION
 		       "Attribute to determine whether the port can be normally enabled." 
                       ::=  { ecsSecureRLCEntry 4 }

               ecsSecRLCNTKState OBJECT-TYPE
                       SYNTAX INTEGER {
				other(1),
                                disabled(2), -- Need to Know is disabled
                                enabled(3)  -- Need to know is enabled 
                              }
                       ACCESS read-write
                       STATUS mandatory
 		       DESCRIPTION
 		       "Attribute to determine whether the Need to Know
 			feature is enabled on the secure Repeater Line Card." 
                       ::=  { ecsSecureRLCEntry 5 }

               ecsSecRLCBroadState OBJECT-TYPE
                       SYNTAX INTEGER {
				other(1),
                                disabled(2), -- Broadcasts are not allowed
                                enabled(3)    -- Broadcasts are allowed 
                              }
                       ACCESS read-write
                       STATUS mandatory
 		       DESCRIPTION
 		       "Attribute to determine whether broadcasts are allowed
 			or not allowed to be transmitted." 
                       ::=  { ecsSecureRLCEntry 6 }

               ecsSecRLCMultiState OBJECT-TYPE
                       SYNTAX INTEGER {
				other(1),
                                disabled(2), -- Multicasts are not allowed
                                enabled(3)    -- Multicasts are allowed 
                              }
                       ACCESS read-write
                       STATUS mandatory
 		       DESCRIPTION
 		       "Attribute to determine whether multicasts are allowed
 			or not allowed to be transmitted." 
                       ::=  { ecsSecureRLCEntry 7 }

               ecsSecRLCLearnMode OBJECT-TYPE
                       SYNTAX INTEGER {
                                off(1),      -- no learning, address is managed
			        single(2),   -- first incoming packet is learnt
                                continual(3) -- address is continually learning 
                              }
                       ACCESS read-write
                       STATUS mandatory
 		       DESCRIPTION
 		       "Attribute to determine the learning
 			mode of the secure repeater line card." 
                       ::=  { ecsSecureRLCEntry 8 }

               ecsSecRLCReportMode OBJECT-TYPE
                       SYNTAX INTEGER {
                                off(1), 	-- Not in applicable learn state
				reportonly(2),		-- Report only
      				disconnectandreport(3) -- Disconnect and Report
                              }
                       ACCESS read-write
                       STATUS mandatory
 		       DESCRIPTION
 		       "Attribute to determine the reporting
 			mode of the secure repeater line card." 
                       ::=  { ecsSecureRLCEntry 9 }


               ecsSecRLCMACAddress OBJECT-TYPE
                       SYNTAX OCTET STRING
                       ACCESS read-write
                       STATUS mandatory
 		       DESCRIPTION
 		       "The MAC address in use by the secure repeater line card." 
                       ::=  { ecsSecureRLCEntry 10 }


--
--  REPEATER LINE CARD GROUP (SLOT, PORT) Table { ecs 5 }
--

-- ecsRLC 1 PortStatistics

               ecsRLCPortStatisticsTable OBJECT-TYPE
                       SYNTAX  SEQUENCE OF ECSRLCPortStatisticsEntry
                       ACCESS  not-accessible
                       STATUS  mandatory
 		       DESCRIPTION
 		       "A table which summaries the statistics for each active port/slot" 
                       ::= { ecsRepeaterLineCard 1 }

               ecsRLCPortStatisticsEntry OBJECT-TYPE
                       SYNTAX  ECSRLCPortStatisticsEntry
                       ACCESS  not-accessible
                       STATUS  mandatory
DESCRIPTION ""
                       INDEX   { ecsRepeaterSlotIndex, ecsRepeaterPortIndex } 
                       ::= { ecsRLCPortStatisticsTable 1 }

                ECSRLCPortStatisticsEntry ::= SEQUENCE {
		       ecsRepeaterSlotIndex    			
			  INTEGER,	
		       ecsRepeaterPortIndex    			
			  INTEGER,
		       ecsRepeaterPortState    			
			  INTEGER,	
		       ecsRepeaterPartitionState
			  INTEGER,	
		       ecsGoodRcvdFrames
			  Counter,
		       ecsTotalByteCount
			  Counter,
		       ecsTotalErrorCount
			  Counter,
		       ecsRxBroadcastFrames
			  Counter,
		       ecsRxMulticastFrames
			  Counter
		      }

               ecsRepeaterSlotIndex OBJECT-TYPE
                       SYNTAX INTEGER
                       ACCESS read-only
                       STATUS mandatory
 		       DESCRIPTION
 		       "The repeater slot index." 
                       ::=  { ecsRLCPortStatisticsEntry 1 }

               ecsRepeaterPortIndex OBJECT-TYPE
                       SYNTAX INTEGER
                       ACCESS read-only
                       STATUS mandatory
 		       DESCRIPTION
 		       "The repeater port index." 
                       ::=  { ecsRLCPortStatisticsEntry 2 }

               ecsRepeaterPortState OBJECT-TYPE
                       SYNTAX INTEGER {
                                        disabled(1),   -- Repeater port will repeat traffic
                                        enabled(2),  -- Repeater port will not repeat traffic
			                disabled-linkdown(3),
			                enabled-linkdown(4),
			                disabled-linkup(5),
			                enabled-linkup(6)
                              }
                       ACCESS read-write
                       STATUS mandatory
 		       DESCRIPTION
 		       "The repeater port state." 
                       ::=  { ecsRLCPortStatisticsEntry 3 }

               ecsRepeaterPartitionState OBJECT-TYPE
                       SYNTAX INTEGER {
                                         on(1),  -- Repeater port is not partitioned
                                         partitioned(2)  -- Repeater port is partitioned
                        }
                       ACCESS read-only
                       STATUS mandatory
 		       DESCRIPTION
 		       "The repeater port partition state." 
                       ::=  { ecsRLCPortStatisticsEntry 4 }

               ecsGoodRcvdFrames OBJECT-TYPE
                       SYNTAX              Counter
                       ACCESS read-only
                       STATUS mandatory
 		       DESCRIPTION
 		       "The number of good frames which have been received and repeted
                       by the specified port." 
                       ::=  { ecsRLCPortStatisticsEntry 5 }

               ecsTotalByteCount OBJECT-TYPE
                       SYNTAX             Counter 
                       ACCESS read-only
                       STATUS mandatory
 		       DESCRIPTION
 		       "The summation of the total number of bytes which have been
                       received in good frames and repeated by the specified port." 
                       ::=  { ecsRLCPortStatisticsEntry 6 }

              ecsTotalErrorCount OBJECT-TYPE
                       SYNTAX              Counter
                       ACCESS read-only
                       STATUS mandatory
 		       DESCRIPTION
 		       "The summaration of all of the errors recorded in the PortErrors
 		       table for the specified port" 
                       ::=  { ecsRLCPortStatisticsEntry 7 }

              ecsRxBroadcastFrames OBJECT-TYPE
                       SYNTAX Counter
                       ACCESS read-only
                       STATUS mandatory
 		       DESCRIPTION
 		       "The number of broadcast frames received on this port." 
                       ::=  { ecsRLCPortStatisticsEntry 8 }

              ecsRxMulticastFrames OBJECT-TYPE
                       SYNTAX Counter
                       ACCESS read-only
                       STATUS mandatory
 		       DESCRIPTION
 		       "The number of broadcast frames received on this port." 
                       ::=  { ecsRLCPortStatisticsEntry 9 }

-- ecsRLC 2

               ecsRLCPortErrorTable OBJECT-TYPE
                       SYNTAX  SEQUENCE OF ECSRLCPortErrorEntry
                       ACCESS  not-accessible
                       STATUS  mandatory
 		       DESCRIPTION
 		       "A table which summaries the error counts for each active port and slot" 
                       ::= { ecsRepeaterLineCard 2 }
 
               ecsRLCPortErrorEntry OBJECT-TYPE
                       SYNTAX  ECSRLCPortErrorEntry 
                       ACCESS  not-accessible  
                       STATUS  mandatory
DESCRIPTION ""
                       INDEX   { ecsErrorSlotIndex,  ecsErrorPortIndex  }
                       ::= { ecsRLCPortErrorTable 1 }  
 
               ECSRLCPortErrorEntry ::= SEQUENCE {
		       ecsErrorSlotIndex
			  INTEGER,
		       ecsErrorPortIndex
			  INTEGER,
		       ecsCollisionsCount
			  Counter,
		       ecsPartitions
			  Counter,
		       ecsCarrierSenseErrors
			  Counter,
		       ecsAlignErrors
			  Counter,
		       ecsCRCErrors
			  Counter,	
		       ecsJabberErrors
			  Counter
		      }
 
               ecsErrorSlotIndex OBJECT-TYPE
                       SYNTAX INTEGER
                       ACCESS read-only
                       STATUS mandatory
 		       DESCRIPTION
 		       "The repeater slot index" 
                       ::=  { ecsRLCPortErrorEntry 1 }

               ecsErrorPortIndex OBJECT-TYPE
                       SYNTAX INTEGER
                       ACCESS read-only
                       STATUS mandatory
 		       DESCRIPTION
 		       "The repeater port index." 
                       ::=  { ecsRLCPortErrorEntry 2 }
   
               ecsCollisionsCount OBJECT-TYPE
                       SYNTAX Counter
                       ACCESS read-only
                       STATUS mandatory
 		       DESCRIPTION
 		       "A count of every attempt to transmit a frame that involved a
                       collision." 
                       ::=  { ecsRLCPortErrorEntry 3 }

               ecsPartitions OBJECT-TYPE
                       SYNTAX Counter
                       ACCESS read-only
                       STATUS mandatory
 		       DESCRIPTION
 		       "The count of the number of partitions which  have been
                       detected by the specified port." 
                       ::=  { ecsRLCPortErrorEntry 4 }

               ecsCarrierSenseErrors OBJECT-TYPE
                       SYNTAX Counter
                       ACCESS read-only
                       STATUS mandatory
 		       DESCRIPTION
 		       "The  number of carrier sense errors which have been detected
                        by the specified port." 
                       ::=  { ecsRLCPortErrorEntry 5 }

               ecsAlignErrors OBJECT-TYPE
                       SYNTAX Counter
                       ACCESS read-only
                       STATUS mandatory
 		       DESCRIPTION
 		       "The number of frames with alignment errors which have been
                       received by the specified port." 
                       ::=  { ecsRLCPortErrorEntry 6 }

               ecsCRCErrors OBJECT-TYPE
                       SYNTAX Counter
                       ACCESS read-only
                       STATUS mandatory
 		       DESCRIPTION
 		       "The number of frames with CRC errors which have been received
                       by the specified port." 
                       ::=  { ecsRLCPortErrorEntry 7 }

               ecsJabberErrors OBJECT-TYPE
                       SYNTAX Counter
                       ACCESS read-only
                       STATUS mandatory
 		       DESCRIPTION
 		       "The  number of jabber errors which have been detected by the
                       specified port." 
                       ::=  { ecsRLCPortErrorEntry 8 }

-- ecsRLC 3

               ecsRLCPortInfoTable OBJECT-TYPE
                       SYNTAX  SEQUENCE OF ECSRLCPortInfoEntry
                       ACCESS  not-accessible
                       STATUS  mandatory
 		       DESCRIPTION
 		       "A table which summaries the status information for each active
                        port/slot" 
                       ::= { ecsRepeaterLineCard 3 }
 
               ecsRLCPortInfoEntry OBJECT-TYPE
                       SYNTAX  ECSRLCPortInfoEntry 
                       ACCESS  not-accessible  
                       STATUS  mandatory
DESCRIPTION ""
                       INDEX   { ecsInfoSlotIndex,  ecsInfoPortIndex }
                       ::= { ecsRLCPortInfoTable 1 }  
 
               ECSRLCPortInfoEntry ::= SEQUENCE {
		       ecsInfoSlotIndex
			  INTEGER,
		       ecsInfoPortIndex
			  INTEGER,
		       ecsInfoPortName
			  DisplayString,
                       ecsRepeaterPartitionAlgor
		          INTEGER,
		       ecsJabberLockProtect
			  INTEGER,
		       ecsPortTest
			  INTEGER,
		       ecsPortErrorState                            
                	  INTEGER,
		       ecsPortReset
			  INTEGER,
		       ecsPortPartitionTraps
			  INTEGER,
		       ecsPortLinkTraps
			  INTEGER,
		       ecsPortBootState
			  INTEGER,
		       ecsPortSLMode
			  INTEGER
		      }

               ecsInfoSlotIndex OBJECT-TYPE
                       SYNTAX INTEGER
                       ACCESS read-only
                       STATUS mandatory
 		       DESCRIPTION
 		       "The repeater slot index" 
                       ::=  { ecsRLCPortInfoEntry 1 }

               ecsInfoPortIndex OBJECT-TYPE
                       SYNTAX INTEGER
                       ACCESS read-only
                       STATUS mandatory
 		       DESCRIPTION
 		       "The repeater port index" 
                       ::=  { ecsRLCPortInfoEntry 2 }



               ecsInfoPortName OBJECT-TYPE
                       SYNTAX DisplayString (SIZE (0..16))
                       ACCESS read-write
                       STATUS mandatory
 		       DESCRIPTION
 		       "This is an informational string that could be used to show
                       the name of a port."
                       ::=   { ecsRLCPortInfoEntry 3 }  


 
               ecsRepeaterPartitionAlgor OBJECT-TYPE
                       SYNTAX INTEGER {
                                         enabled(1),      --      Partition Algorithm is enabled
                                         disabled(2)     --      Partition Algorithm is disabled
                              }
                       ACCESS read-write
                       STATUS mandatory
 		       DESCRIPTION
 		       "The current state of the repeater port algorithm." 
                       ::=  { ecsRLCPortInfoEntry 4}

               ecsJabberLockProtect OBJECT-TYPE
                       SYNTAX INTEGER {
                                         enabled(1),      -- Enabled Jabber Lockup protect switch
                                                          -- is enabled
                                         disabled(2)     -- Disabled Jabber Lockup protect switch
                                                          -- is disabled
                              }
                       ACCESS read-write
                       STATUS mandatory
 		       DESCRIPTION
 		       "The current state of the jabber protect switch. This affects
                       all ports on the repeater ULA (not necessarily all ports
                       on the card)." 
                       ::=  { ecsRLCPortInfoEntry 5 }

               ecsPortTest OBJECT-TYPE
                       SYNTAX INTEGER {
				         not-in-test(1),
				         test(2),
				         passed(3),
				         failed(4)
                              }
                       ACCESS read-write
                       STATUS mandatory
 		       DESCRIPTION
 		       "The Loopback test is performed on the specified port. This will
                       interrupt traffic on all ports on the repeater ULA
                       (not necessarily all ports on the card in a specified slot)
                       while the test is in progress." 
                       ::=  { ecsRLCPortInfoEntry 6 }

               ecsPortErrorState OBJECT-TYPE
                       SYNTAX INTEGER {
                                         none(1), 		-- none of the following
                                         normal(2), 		-- normal state, no errors
                                         hi-collision(3), 	-- Hi Collision rate
                                         partition(4), 		-- Partition occured
                                         high-crc-errorrate(5), 		-- CRC error rate exceeded
                                         high-alignment-errorrate(6), 	-- Alignment error
                                         high-traffic-rate(7), 		-- Traffic rate exceeded
                                         high-jabber-errorrate(8), 		-- Hi jabber rate
                                         high-carriersense-errorrate(9), 		-- Hi carrier sense rate
					 unpartitioned(10),	-- Port has unpartitioned
				         linkstatechange-up(11),
				         linkstatechange-down(12),
					 acknowledged(255)
                               }
                       ACCESS read-write
                       STATUS mandatory		   
 		       DESCRIPTION
 		       "The error status of the specified port. Under normal conditions this takes
 			the value 'normal' specifying that no error condition has been detected."  
	               ::=  { ecsRLCPortInfoEntry 7 }

               ecsPortReset OBJECT-TYPE
                       SYNTAX INTEGER {
				         not-reset(1),
				         reset(2)
                              }
                       ACCESS read-write
                       STATUS mandatory
 		       DESCRIPTION
 		       "The specified port is reset. This will
                       interrupt traffic on all ports on the repeater ULA
                       (not necessarily all ports on the card in a specified slot)
                       while the reset is in progress." 
                       ::=  { ecsRLCPortInfoEntry 8 }

               ecsPortPartitionTraps OBJECT-TYPE
                       SYNTAX INTEGER {
                                         yes(1),      -- Partition Traps will be sent
                                         no(2)        -- Partition Traps will not be sent
                                                      -- is disabled
                              }
                       ACCESS read-write
                       STATUS mandatory
 		       DESCRIPTION
 		       "Determines whether partition traps will be sent for this port." 
                       ::=  { ecsRLCPortInfoEntry 9 }

               ecsPortLinkTraps OBJECT-TYPE
                       SYNTAX INTEGER {
                                         yes(1),    -- Link Traps will be sent
                                         no(2),     -- Link Traps will not be sent
                                                    -- is disabled
			                 not-applicable(3) -- Not an appropriate port
                              }
                       ACCESS read-write
                       STATUS mandatory
 		       DESCRIPTION
 		       "Determines whether link traps will be sent for this port." 
                       ::=  { ecsRLCPortInfoEntry 10 }

               ecsPortBootState OBJECT-TYPE
                       SYNTAX INTEGER {
                                         disabled(1), 	  -- disabled on boot
                                         enabled(2)	  -- enabled on boot
                              }
                       ACCESS read-only
                       STATUS mandatory
 		       DESCRIPTION
 		       "Determines whether the port is disabled on boot (DOB),
 			and therefore suitable for resilient link use." 
                       ::=  { ecsRLCPortInfoEntry 11 }


               ecsPortSLMode OBJECT-TYPE
                       SYNTAX INTEGER {
                                         on(1), 
                                         off(2)
                              }
                       ACCESS read-write
                       STATUS mandatory
 		       DESCRIPTION
 		       "Determines whether station locate is enabled 
 			for this port." 
                       ::=  { ecsRLCPortInfoEntry 12 }


-- ecs 4

               ecsRLCcrcTable OBJECT-TYPE
                       SYNTAX  SEQUENCE OF ECSRLCcrcEntry
                       ACCESS  not-accessible
                       STATUS  mandatory
 		       DESCRIPTION
 		       "Level at which port rate error rate trap is produced." 
                       ::= { ecsRepeaterLineCard 4 }

               ecsRLCcrcEntry OBJECT-TYPE
                       SYNTAX  ECSRLCcrcEntry
                       ACCESS  not-accessible
                       STATUS  mandatory
 		       DESCRIPTION
 		       "The number of frames with CRC errors which have been received
                        by the specified port."
                       INDEX   {  ecsCRCSlotIndex, ecsCRCPortIndex }
                       ::= { ecsRLCcrcTable 1 }

               ECSRLCcrcEntry ::= SEQUENCE {
		       ecsCRCSlotIndex
			  INTEGER,
		       ecsCRCPortIndex
			  INTEGER,
		       ecsCRCErrorRate
			  Gauge,
		       ecsCRCThreshold
			  INTEGER,	        -- error rate trap is produced.
		       ecsCRCDecRateValue
			  INTEGER,
		       ecsCRCDecRateUnits
		          INTEGER,
		       ecsCRCHysteresisValue	-- Specifies the value to 
						-- which the CRC error 
						-- gauge must fall before 
						-- another crossing of the 
						-- threshold results in a trap.
			  INTEGER
	       }

               ecsCRCSlotIndex OBJECT-TYPE
                       SYNTAX INTEGER
                       ACCESS read-only
                       STATUS mandatory
 		       DESCRIPTION
 		       "The repeater slot index" 
                       ::=  { ecsRLCcrcEntry 1 }

               ecsCRCPortIndex OBJECT-TYPE
                       SYNTAX INTEGER
                       ACCESS read-only
                       STATUS mandatory
 		       DESCRIPTION
 		       "The repeater port index" 
                       ::=  { ecsRLCcrcEntry 2 }

               ecsCRCErrorRate OBJECT-TYPE
                       SYNTAX Gauge
                       ACCESS read-only
                       STATUS mandatory

 		       DESCRIPTION
 		       "The gauge representing the CRC error rate. This is configured
                       using the CRC error rate configuration."
                       ::= { ecsRLCcrcEntry 3 }

               ecsCRCThreshold OBJECT-TYPE
                       SYNTAX INTEGER             
                       ACCESS read-write
                       STATUS mandatory
 		       DESCRIPTION
 		       "Level at which port rate error rate trap is produced." 
                       ::= { ecsRLCcrcEntry 4 }

               ecsCRCDecRateValue OBJECT-TYPE
                       SYNTAX INTEGER             
                       ACCESS read-write
                       STATUS mandatory
 		       DESCRIPTION
 		       "VALUE that, along with Rate Units, determines the Rate
 			Interval, (in ns) between decrements of the CRC error guage, 
 			Rate Interval = ( Units * Value )." 
                       ::= { ecsRLCcrcEntry 5 }

               ecsCRCDecRateUnits OBJECT-TYPE
                       SYNTAX 	INTEGER  {
				other(1),	-- none of the following
				microseconds(2),
				milliseconds(3),
				seconds(4),
				minutes(5),
				hours(6),
				days(7)
		       }		           
                       ACCESS read-write
                       STATUS mandatory
 		       DESCRIPTION
 		       "UNITS that, along with Rate value, determine the Rate
 			Interval Rate Interval = ( Units * Value )" 
                       ::= { ecsRLCcrcEntry 6 }


               ecsCRCHysteresisValue OBJECT-TYPE
                       SYNTAX INTEGER             
                       ACCESS read-write
                       STATUS mandatory
 		       DESCRIPTION
 		       "Specifies the value to which the CRC error guage must fall
                       before another crossing of the threshold results in a trap." 
                       ::= { ecsRLCcrcEntry 7 }

-- ecs 5

               ecsRLCtrafficTable OBJECT-TYPE
                       SYNTAX  SEQUENCE OF ECSRLCtrafficEntry
                       ACCESS  not-accessible
                       STATUS  mandatory
 		       DESCRIPTION
 		       "The configuration parameters which must be set up in order to
                       use the traffic rate guage." 
                       ::= { ecsRepeaterLineCard 5 }

               ecsRLCtrafficEntry OBJECT-TYPE
                       SYNTAX  ECSRLCtrafficEntry
                       ACCESS  not-accessible
                       STATUS  mandatory
 		       DESCRIPTION
 		       ""
                       INDEX   { ecsTrafficSlotIndex, ecsTrafficPortIndex } 
                       ::= { ecsRLCtrafficTable 1 }

              ECSRLCtrafficEntry ::= SEQUENCE {
		       ecsTrafficSlotIndex
			  INTEGER,
		       ecsTrafficPortIndex
			  INTEGER,
 		       ecsTrafficRate
			  Gauge,
		       ecsTrafficThreshold	  -- level at which High Traffic
						  -- error rate trap is produced.
			  INTEGER, 
		       ecsTrafficDecRateValue
			  INTEGER,
		       ecsTrafficDecRateUnits
		          INTEGER,

		       ecsTrafficHysteresisValue  -- Specifies the value to 
						  -- which the
						  -- traffic  guage must fall 
						  -- before another crossing 
						  -- of the threshold results 
						  -- in a trap.
			  INTEGER	
	       }

               ecsTrafficSlotIndex OBJECT-TYPE
                       SYNTAX INTEGER
                       ACCESS read-only
                       STATUS mandatory
 		       DESCRIPTION
 		       "The repeater slot index" 
                       ::=  { ecsRLCtrafficEntry 1 }

               ecsTrafficPortIndex OBJECT-TYPE
                       SYNTAX INTEGER
                       ACCESS read-only
                       STATUS mandatory
 		       DESCRIPTION
 		       "The repeater port index" 
                       ::=  { ecsRLCtrafficEntry 2 }

               ecsTrafficRate OBJECT-TYPE
                       SYNTAX Gauge
                       ACCESS read-only
                       STATUS mandatory
 		       DESCRIPTION
 		       "The gauge representing the rate at which good frames have been
                       received and repeated.  This is configured using the traffic
                       rate configuration." 
                       ::=  { ecsRLCtrafficEntry 3 }  

               ecsTrafficThreshold OBJECT-TYPE
                       SYNTAX INTEGER             
                       ACCESS read-write
                       STATUS mandatory
 		       DESCRIPTION
 		       "Level at which port rate error rate trap is produced." 
                       ::=  { ecsRLCtrafficEntry 4 }



               ecsTrafficDecRateValue OBJECT-TYPE
                       SYNTAX INTEGER             
                       ACCESS read-write
                       STATUS mandatory
 		       DESCRIPTION
 		       "VALUE that, along with Rate Units, determines the Rate
 			Interval, (in ns) between decrements of the CRC error guage, 
 			Rate Interval = ( Units * Value )." 
                       ::= { ecsRLCtrafficEntry 5 }

               ecsTrafficDecRateUnits OBJECT-TYPE
                       SYNTAX 	INTEGER  {
				other(1),	-- none of the following
				microseconds(2),
				milliseconds(3),
				seconds(4),
				minutes(5),
				hours(6),
				days(7)
		       }		           
                       ACCESS read-write
                       STATUS mandatory
 		       DESCRIPTION
 		       "UNITS that, along with Rate value, determine the Rate
 			Interval Rate Interval = ( Units * Value )" 
                       ::= { ecsRLCtrafficEntry 6 }


              ecsTrafficHysteresisValue OBJECT-TYPE
                       SYNTAX 		INTEGER             
                       ACCESS read-write
                       STATUS mandatory
 		       DESCRIPTION
 		       "Specifies the value to which the CRC error guage must fall
                       before another crossing of the threshold results in a trap." 
                       ::=  { ecsRLCtrafficEntry 7 }


-- ecs 6
    
               ecsRLCcollisionTable OBJECT-TYPE
                       SYNTAX  SEQUENCE OF ECSRLCcollisionEntry
                       ACCESS  not-accessible
		       STATUS  mandatory
 		       DESCRIPTION
 		       "The configuration parameters which must be set up in order
                       to use the collision rate guage." 
                       ::= { ecsRepeaterLineCard 6 }

               ecsRLCcollisionEntry OBJECT-TYPE
                       SYNTAX  ECSRLCcollisionEntry
                       ACCESS  not-accessible
                       STATUS  mandatory
DESCRIPTION ""
                       INDEX   { ecsCollisionSlotIndex, ecsCollisionPortIndex }
                       ::= { ecsRLCcollisionTable 1 }

               ECSRLCcollisionEntry ::= SEQUENCE {
		       ecsCollisionSlotIndex
			  INTEGER,
		       ecsCollisionPortIndex
			  INTEGER,
  		       ecsCollisionRate          
	                  Gauge,             

	               ecsCollisionThreshold	    -- level at which High Collision
						    -- error rate trap is produced.
			  INTEGER,
 
		       ecsCollisionDecRateValue
			  INTEGER,
		       ecsCollisionDecRateUnits
		          INTEGER,

		       ecsCollisionHysteresisValue  -- Specifies the value to 
						    -- which the
						    -- collision  guage must 
						    -- fall before another
						    -- crossing of the 
						    -- threshold results in
						    -- a trap.
			  INTEGER

	       }

               ecsCollisionSlotIndex OBJECT-TYPE
                       SYNTAX INTEGER
                       ACCESS read-only
                       STATUS mandatory
 		       DESCRIPTION
 		       "The repeater slot index" 
                       ::=  { ecsRLCcollisionEntry 1 }

               ecsCollisionPortIndex OBJECT-TYPE
                       SYNTAX INTEGER
                       ACCESS read-only
                       STATUS mandatory
 		       DESCRIPTION
 		       "The repeater port index" 
                       ::=  { ecsRLCcollisionEntry 2 }


               ecsCollisionRate OBJECT-TYPE
                       SYNTAX Gauge
                       ACCESS read-only
                       STATUS mandatory
 		       DESCRIPTION
 		       "The gauge representing the rate at which collisions have been
                       detected. This is configured using the collision rate
                       configuration." 
                       ::=  { ecsRLCcollisionEntry 3 }  

               ecsCollisionThreshold OBJECT-TYPE
                       SYNTAX INTEGER             
                       ACCESS read-write
                       STATUS mandatory
 		       DESCRIPTION
 		       "Level at which the collision rate guage will produce a
                       High Collision rate trap." 
                       ::=  { ecsRLCcollisionEntry 4 }

               ecsCollisionDecRateValue OBJECT-TYPE
                       SYNTAX INTEGER             
                       ACCESS read-write
                       STATUS mandatory
 		       DESCRIPTION
 		       "VALUE that, along with Rate Units, determines the Rate
 			Interval, (in ns) between decrements of the CRC error guage, 
 			Rate Interval = ( Units * Value )." 
                       ::= { ecsRLCcollisionEntry 5 }

               ecsCollisionDecRateUnits OBJECT-TYPE
                       SYNTAX 	INTEGER  {
				other(1),	-- none of the following
				microseconds(2),
				milliseconds(3),
				seconds(4),
				minutes(5),
				hours(6),
				days(7)
		       }		           
                       ACCESS read-write
                       STATUS mandatory
 		       DESCRIPTION
 		       "UNITS that, along with Rate value, determine the Rate
 			Interval Rate Interval = ( Units * Value )" 
                       ::= { ecsRLCcollisionEntry 6 }


               ecsCollisionHysteresisValue OBJECT-TYPE
                       SYNTAX INTEGER             
                       ACCESS read-write
                       STATUS mandatory
 		       DESCRIPTION
 		       "Specifies the value to which the Collision guage must fall
                       before another crossing of the threshold results in a trap." 
                       ::=  { ecsRLCcollisionEntry 7 }


-- ecs 7

               ecsRLCjabberTable OBJECT-TYPE
                       SYNTAX  SEQUENCE OF ECSRLCjabberEntry
                       ACCESS  not-accessible
                       STATUS  mandatory
 		       DESCRIPTION
 		       "The configuration parameters which must be set up in
                       order to use the jabber rate guage." 
                       ::= { ecsRepeaterLineCard 7 }

               ecsRLCjabberEntry OBJECT-TYPE
                       SYNTAX  ECSRLCjabberEntry
                       ACCESS  not-accessible
                       STATUS  mandatory
DESCRIPTION ""
                       INDEX   { ecsJabberSlotIndex, ecsJabberPortIndex } 
                       ::= { ecsRLCjabberTable 1 }

               ECSRLCjabberEntry ::= SEQUENCE {
		       ecsJabberSlotIndex
			  INTEGER,
		       ecsJabberPortIndex
			  INTEGER,
  		       ecsJabberErrorRate       
			  Gauge,

		       ecsJabberThreshold	 -- level at which High Jabber
						 -- error rate trap is produced.
			  INTEGER,
 		       ecsJabberDecRateValue
			  INTEGER,
		       ecsJabberDecRateUnits
		          INTEGER,

		       ecsJabberHysteresisValue  -- Specifies the value to 
						 -- which the
						 -- jabber error  guage must 
						 -- fall before another 
						 -- crossing of the 
						 -- threshold results in
						 -- a trap.
			  INTEGER
	       }

               ecsJabberSlotIndex OBJECT-TYPE
                       SYNTAX INTEGER
                       ACCESS read-only
                       STATUS mandatory
 		       DESCRIPTION
 		       "The repeater slot index" 
                       ::=  { ecsRLCjabberEntry 1 }

               ecsJabberPortIndex OBJECT-TYPE
                       SYNTAX INTEGER
                       ACCESS read-only
                       STATUS mandatory
 		       DESCRIPTION
 		       "The repeater port index" 
                       ::=  { ecsRLCjabberEntry 2 }

               ecsJabberErrorRate OBJECT-TYPE
                       SYNTAX Gauge
                       ACCESS read-only
                       STATUS mandatory
 		       DESCRIPTION
 		       "The gauge representing the rate at which jabber errors
                       have been detected. This is configured using the jabber
                       rate configuration." 
                       ::=  { ecsRLCjabberEntry 3 }  

               ecsJabberThreshold OBJECT-TYPE
                       SYNTAX INTEGER             
                       ACCESS read-write
                       STATUS mandatory
 		       DESCRIPTION
 		       "Level at which port rate error rate trap is produced." 
                       ::= 	{ ecsRLCjabberEntry 4 }

               ecsJabberDecRateValue OBJECT-TYPE
                       SYNTAX INTEGER             
                       ACCESS read-write
                       STATUS mandatory
 		       DESCRIPTION
 		       "VALUE that, along with Rate Units, determine the Rate
 			Interval, Rate Interval = ( Units * Value )"  
                       ::= { ecsRLCjabberEntry 5 }

               ecsJabberDecRateUnits OBJECT-TYPE
                       SYNTAX 	INTEGER  {
				other(1),	-- none of the following
				microseconds(2),
				milliseconds(3),
				seconds(4),
				minutes(5),
				hours(6),
				days(7)
		       }		           
                       ACCESS read-write
                       STATUS mandatory
 		       DESCRIPTION
 		       "UNITS that, along with Rate value, determine the Rate
 			Interval Rate Interval = ( Units * Value )" 
                       ::= { ecsRLCjabberEntry 6 }



               ecsJabberHysteresisValue OBJECT-TYPE
                       SYNTAX INTEGER             
                       ACCESS read-write
                       STATUS mandatory
 		       DESCRIPTION
 		       "Specifies the value to which the jabber error guage must
                       fall before another crossing of the threshold results in a trap." 
                       ::=  { ecsRLCjabberEntry 7 }

-- ecs 8

               ecsRLCalignTable OBJECT-TYPE
                       SYNTAX  SEQUENCE OF ECSRLCalignEntry
                       ACCESS  not-accessible
		       STATUS  mandatory
 		       DESCRIPTION
 		       "The configuration parameters which must be set up in order to
                       use the alignment error rate guage." 
                       ::= { ecsRepeaterLineCard 8 }

              ecsRLCalignEntry OBJECT-TYPE
                       SYNTAX  ECSRLCalignEntry
                       ACCESS  not-accessible
                       STATUS  mandatory
DESCRIPTION ""
                       INDEX   {  ecsAlignSlotIndex, ecsAlignPortIndex } 
                       ::= { ecsRLCalignTable 1 }

              ECSRLCalignEntry ::= SEQUENCE {
		       ecsAlignSlotIndex
			  INTEGER,
		       ecsAlignPortIndex
			  INTEGER,
		       ecsAlignErrorRate
			  Gauge,
		       ecsAlignThreshold         -- level at which High Alignment
						 -- error rate trap is produced.
			  INTEGER,
 		       ecsAlignDecRateValue
			  INTEGER,
		       ecsAlignDecRateUnits
		          INTEGER,

		       ecsAlignHysteresisValue   -- Specifies the value to  
						 -- which the alignment 
						 -- error guage must fall 
						 -- before another crossing 
						 -- of the threshold 
						 -- results in a trap.
			  INTEGER
	       }

               ecsAlignSlotIndex OBJECT-TYPE
                       SYNTAX INTEGER
                       ACCESS read-only
                       STATUS mandatory
 		       DESCRIPTION
 		       "The repeater slot index" 
                       ::=  { ecsRLCalignEntry 1 }

               ecsAlignPortIndex OBJECT-TYPE
                       SYNTAX INTEGER
                       ACCESS read-only
                       STATUS mandatory
 		       DESCRIPTION
 		       "The repeater port index" 
                       ::=  { ecsRLCalignEntry 2 }

               ecsAlignErrorRate OBJECT-TYPE
                       SYNTAX Gauge
                       ACCESS read-only
                       STATUS mandatory
 		       DESCRIPTION
 		       "The gauge representing the alignment error rate. This is
                       configured using the alignment error rate configuration." 
                       ::=  { ecsRLCalignEntry 3 }  

               ecsAlignThreshold OBJECT-TYPE
                       SYNTAX INTEGER             
                       ACCESS read-write
                       STATUS mandatory
 		       DESCRIPTION
 		       "Level at which port rate error rate trap is produced." 
                       ::= 	{ ecsRLCalignEntry 4 }

               ecsAlignDecRateValue OBJECT-TYPE
                       SYNTAX INTEGER             
                       ACCESS read-write
                       STATUS mandatory
 		       DESCRIPTION
 		       "VALUE that, along with Rate Units, determines the Rate
 			Interval, (in ns) between decrements of the CRC error guage, 
 			Rate Interval = ( Units * Value ), where UNITS are in ns" 
                       ::= { ecsRLCalignEntry 5 }

               ecsAlignDecRateUnits OBJECT-TYPE
                       SYNTAX 	INTEGER  {
				other(1),	-- none of the following
				microseconds(2),
				milliseconds(3),
				seconds(4),
				minutes(5),
				hours(6),
				days(7)
	           	}
                       ACCESS read-write
                       STATUS mandatory
 		       DESCRIPTION
 		       "UNITS that, along with Rate value, determine the Rate
 			Interval Rate Interval = ( Units * Value )" 
                       ::= { ecsRLCalignEntry 6 }


                ecsAlignHysteresisValue OBJECT-TYPE
                       SYNTAX INTEGER             
                       ACCESS read-write
                       STATUS mandatory
 		       DESCRIPTION
 		       "Specifies the value to which the CRC error guage must fall
                       before another crossing of the threshold results in a trap." 
                       ::=  { ecsRLCalignEntry 7 }

-- ecs 9
               ecsRLCcarrierTable OBJECT-TYPE
                       SYNTAX  SEQUENCE OF ECSRLCcarrierEntry
                       ACCESS  not-accessible
                       STATUS  mandatory
 		       DESCRIPTION
 		       "The configuration parameters which must be set up in order
                       to use the carrier sense error rate guage."
                       ::= { ecsRepeaterLineCard 9 }

                       ecsRLCcarrierEntry OBJECT-TYPE
                       SYNTAX  ECSRLCcarrierEntry
                       ACCESS  not-accessible
                       STATUS  mandatory
DESCRIPTION ""
                       INDEX   { ecsCarrierSlotIndex, ecsCarrierPortIndex }  
                       ::= { ecsRLCcarrierTable 1 }

               ECSRLCcarrierEntry ::= SEQUENCE {
		       ecsCarrierSlotIndex
			  INTEGER,
 		       ecsCarrierPortIndex
			  INTEGER,
  		       ecsCarrierSenseErrorRate     
			  Gauge,              

		       ecsCarrierSenseThreshold        -- level at which High Carrier 
						       -- Sense error rate trap is 
						       -- produced.
			  INTEGER, 
		       ecsCarrierSenseRateValue
			  INTEGER,
		       ecsCarrierSenseRateUnits
		          INTEGER,
		       ecsCarrierSenseHysteresisValue  -- Specifies the value 
						       -- to which the 
						       -- carrier sense 
						       -- error guage must 
						       -- fall before another 
						       -- crossing of the
						       -- threshold results
						       -- in a trap.
			  INTEGER
    		    }

               ecsCarrierSlotIndex OBJECT-TYPE
                       SYNTAX INTEGER
                       ACCESS read-only
                       STATUS mandatory
 		       DESCRIPTION
 		       "The repeater slot index" 
                       ::=  { ecsRLCcarrierEntry 1 }

               ecsCarrierPortIndex OBJECT-TYPE
                       SYNTAX INTEGER
                       ACCESS read-only
                       STATUS mandatory
 		       DESCRIPTION
 		       "The repeater port index" 
                       ::=  { ecsRLCcarrierEntry 2 }

               ecsCarrierSenseErrorRate OBJECT-TYPE
                       SYNTAX Gauge
                       ACCESS read-only
                       STATUS mandatory
 		       DESCRIPTION
 		       "The gauge representing the rate at which jabber errors have
                       been detected. This is configured using the jabber rate
                       configuration." 
                       ::=  { ecsRLCcarrierEntry 3 }  

               ecsCarrierSenseThreshold OBJECT-TYPE
                       SYNTAX INTEGER             
                       ACCESS read-write
                       STATUS mandatory
 		       DESCRIPTION
 		       "Level at which port rate error rate trap is produced." 
                       ::=  { ecsRLCcarrierEntry 4 }

               ecsCarrierSenseRateValue OBJECT-TYPE
                       SYNTAX INTEGER             
                       ACCESS read-write
                       STATUS mandatory
 		       DESCRIPTION
 		       "VALUE that, along with Rate Units, determines the Rate
 			Interval, (in ns) between decrements of the CRC error guage, 
 			Rate Interval = ( Units * Value )."
                       ::= { ecsRLCcarrierEntry 5 }

               ecsCarrierSenseRateUnits OBJECT-TYPE
                       SYNTAX 	INTEGER  {
				other(1),	-- none of the following
				microseconds(2),
				milliseconds(3),
				seconds(4),
				minutes(5),
				hours(6),
				days(7)
		       }			           
                       ACCESS read-write
                       STATUS mandatory
 		       DESCRIPTION
 		       "UNITS that, along with Rate value, determine the Rate
 			Interval Rate Interval = ( Units * Value )" 
                       ::= { ecsRLCcarrierEntry 6 }

               ecsCarrierSenseHysteresisValue OBJECT-TYPE
                       SYNTAX INTEGER             
                       ACCESS read-write
                       STATUS mandatory
 		       DESCRIPTION
 		       "Specifies the value to which the carrier sense error guage
                       must fall before another crossing of the threshold results
                       in a trap." 
                       ::=  { ecsRLCcarrierEntry 7 }

-- { ecsRepeaterLineCard 10 } - statistics on a per slot basis

               ecsRLCSlotStatisticsTable OBJECT-TYPE
                       SYNTAX  SEQUENCE OF ECSRLCSlotStatisticsEntry
                       ACCESS  not-accessible
                       STATUS  mandatory
 		       DESCRIPTION
 		       "A table which summaries the statistics for each active slot" 
                       ::= { ecsRepeaterLineCard 10 }

               ecsRLCSlotStatisticsEntry OBJECT-TYPE
                       SYNTAX  ECSRLCSlotStatisticsEntry
                       ACCESS  not-accessible
                       STATUS  mandatory
DESCRIPTION ""
                       INDEX   { ecsRLCSlotIndex } 
                       ::= { ecsRLCSlotStatisticsTable 1 }

                ECSRLCSlotStatisticsEntry ::= SEQUENCE {
		       ecsRLCSlotIndex    			
			  INTEGER,		
		       ecsRLCGoodRcvdFrames
			  Counter,
		       ecsRLCTotalByteCount
			  Counter,
		       ecsRLCTotalErrorCount
			  Counter,
		       ecsRLCTotalBroadcasts
			  Counter,
		       ecsRLCTotalMulticasts
			  Counter
		      }

	       ecsRLCSlotIndex OBJECT-TYPE
		       SYNTAX INTEGER
		       ACCESS read-only
		       STATUS mandatory
 		       DESCRIPTION
 		       "The slot number of the Repeater Line Card."
		       ::= { ecsRLCSlotStatisticsEntry 1 }

	       ecsRLCGoodRcvdFrames OBJECT-TYPE
		       SYNTAX Counter
		       ACCESS read-only
		       STATUS mandatory
 		       DESCRIPTION
 		       "The number of readable frames received by this slot."
		       ::= { ecsRLCSlotStatisticsEntry 2 }

	       ecsRLCTotalByteCount OBJECT-TYPE
		       SYNTAX Counter
		       ACCESS read-only
		       STATUS mandatory
 		       DESCRIPTION
 		       "The number of readable octets received by this Repeater Line Card."
		       ::= { ecsRLCSlotStatisticsEntry 3 }

	       ecsRLCTotalErrorCount OBJECT-TYPE
		       SYNTAX Counter
		       ACCESS read-only
		       STATUS mandatory
 		       DESCRIPTION
 		       "The total number of errors received on this slot."
		       ::= { ecsRLCSlotStatisticsEntry 4 }

	       ecsRLCTotalBroadcasts OBJECT-TYPE
		       SYNTAX Counter
		       ACCESS read-only
		       STATUS mandatory
 		       DESCRIPTION
 		       "The total number of broadcast frames received on this slot."
		       ::= { ecsRLCSlotStatisticsEntry 5 }

	       ecsRLCTotalMulticasts OBJECT-TYPE
		       SYNTAX Counter
		       ACCESS read-only
		       STATUS mandatory
 		       DESCRIPTION
 		       "The total number of multicast frames received on this slot."
		       ::= { ecsRLCSlotStatisticsEntry 6 }

-- { ecsRepeaterLineCard 11 } - error statistics on a per slot basis

               ecsRLCSlotErrorTable OBJECT-TYPE
                       SYNTAX  SEQUENCE OF ECSRLCSlotErrorEntry
                       ACCESS  not-accessible
                       STATUS  mandatory
 		       DESCRIPTION
 		       "A table which summaries the error statistics for each active slot" 
                       ::= { ecsRepeaterLineCard 11 }

               ecsRLCSlotErrorEntry OBJECT-TYPE
                       SYNTAX  ECSRLCSlotErrorEntry
                       ACCESS  not-accessible
                       STATUS  mandatory
DESCRIPTION ""
                       INDEX   { ecsRLCErrorSlotIndex } 
                       ::= { ecsRLCSlotErrorTable 1 }

                ECSRLCSlotErrorEntry ::= SEQUENCE {
		       ecsRLCErrorSlotIndex    			
			  INTEGER,		
		       ecsRLCCollisionsCount
			  Counter,
		       ecsRLCPartitions
			  Counter,
		       ecsRLCCarrierSenseErrors
			  Counter,
		       ecsRLCAlignErrors
			  Counter,
		       ecsRLCCRCErrors
			  Counter,	
		       ecsRLCJabberErrors
			  Counter
		      }

	       ecsRLCErrorSlotIndex OBJECT-TYPE
		       SYNTAX INTEGER
		       ACCESS read-only
		       STATUS mandatory
 		       DESCRIPTION
 		       "The slot number of the Repeater Line Card for which these
 			error statistics pertain."
		       ::= { ecsRLCSlotErrorEntry 1 }

	       ecsRLCCollisionsCount OBJECT-TYPE
		       SYNTAX Counter
		       ACCESS read-only
		       STATUS mandatory
 		       DESCRIPTION
 		       "The total number of Collisions Reported for this slot."
		       ::= { ecsRLCSlotErrorEntry 2 }


	       ecsRLCPartitions OBJECT-TYPE
		       SYNTAX Counter
		       ACCESS read-only
		       STATUS mandatory
 		       DESCRIPTION
 		       "The total number of Partitions Reported for this slot."
		       ::= { ecsRLCSlotErrorEntry 3 }

	       ecsRLCCarrierSenseErrors OBJECT-TYPE
		       SYNTAX Counter
		       ACCESS read-only
		       STATUS mandatory
 		       DESCRIPTION
 		       "The total number of Carrier Sense erros reported for this slot."
		       ::= { ecsRLCSlotErrorEntry 4 }

	       ecsRLCAlignErrors OBJECT-TYPE
		       SYNTAX Counter
		       ACCESS read-only
		       STATUS mandatory
 		       DESCRIPTION
 		       "The total number of Alignement errors Reported for this slot."
		       ::= { ecsRLCSlotErrorEntry 5 }

	       ecsRLCCRCErrors OBJECT-TYPE
		       SYNTAX Counter
		       ACCESS read-only
		       STATUS mandatory
 		       DESCRIPTION
 		       "The total number of CRC errors reported for this slot."
		       ::= { ecsRLCSlotErrorEntry 6 }

	       ecsRLCJabberErrors OBJECT-TYPE
		       SYNTAX Counter
		       ACCESS read-only
		       STATUS mandatory
 		       DESCRIPTION
 		       "The total number of jabber errors reported for this slot."
		       ::= { ecsRLCSlotErrorEntry 7 }



--    	ecsHubStatistics    		OBJECT IDENTIFIER ::= { ecs 8 }      
-- 	statistics on a per hub basis

	       ecsHubTotalGoodRcvdFrames OBJECT-TYPE
		       SYNTAX Counter
		       ACCESS read-only
		       STATUS mandatory
 		       DESCRIPTION
 		       "The number of readable frames received by this slot."
		       ::= { ecsHubStatistics 1 }

	       ecsHubTotalByteCount OBJECT-TYPE
		       SYNTAX Counter
		       ACCESS read-only
		       STATUS mandatory
 		       DESCRIPTION
 		       "The number of readable octets received by this hub."
		       ::= { ecsHubStatistics 2 }

	       ecsHubTotalErrorCount OBJECT-TYPE
		       SYNTAX Counter
		       ACCESS read-only
		       STATUS mandatory
 		       DESCRIPTION
 		       "The total number of errored packets detected on the hub."
		       ::= { ecsHubStatistics 3 }

	       ecsHubTotalBroadcasts OBJECT-TYPE
		       SYNTAX Counter
		       ACCESS read-only
		       STATUS mandatory
 		       DESCRIPTION
 		       "The total number of brodcast packets detected on the hub."
		       ::= { ecsHubStatistics 4 }

	       ecsHubTotalMultiFrames OBJECT-TYPE
		       SYNTAX Counter
		       ACCESS read-only
		       STATUS mandatory
 		       DESCRIPTION
 		       "The total number of multicast packets detected on the hub."
		       ::= { ecsHubStatistics 5 }

	       ecsHubTotalCollisionsCount OBJECT-TYPE
		       SYNTAX Counter
		       ACCESS read-only
		       STATUS mandatory
 		       DESCRIPTION
 		       "The total number of Collisions Reported for the hub."
		       ::= { ecsHubStatistics 6 }


	       ecsHubTotalPartitions OBJECT-TYPE
		       SYNTAX Counter
		       ACCESS read-only
		       STATUS mandatory
 		       DESCRIPTION
 		       "The total number of Partitions Reported for this hub."
		       ::= { ecsHubStatistics 7 }

	       ecsHubTotalCarrierSenseErrors OBJECT-TYPE
		       SYNTAX Counter
		       ACCESS read-only
		       STATUS mandatory
 		       DESCRIPTION
 		       "The total number of Carrier Sense erros reported for this hub."
		       ::= { ecsHubStatistics 8 }

	       ecsHubTotalAlignErrors OBJECT-TYPE
		       SYNTAX Counter
		       ACCESS read-only
		       STATUS mandatory
 		       DESCRIPTION
 		       "The total number of Alignement errors reported for this hub."
		       ::= { ecsHubStatistics 9 }

	       ecsHubTotalCRCErrors OBJECT-TYPE
		       SYNTAX Counter
		       ACCESS read-only
		       STATUS mandatory
 		       DESCRIPTION
 		       "The total number of CRC errors reported for this hub."
		       ::= { ecsHubStatistics 10 }

	       ecsHubTotalJabberErrors OBJECT-TYPE
		       SYNTAX Counter
		       ACCESS read-only
		       STATUS mandatory
 		       DESCRIPTION
 		       "The total number of jabber errors reported for this hub."
		       ::= { ecsHubStatistics 11 }

-- ecs RLC Station Locate { ecs 6 }

	       ecsRLCSizeOfStationLocateDB OBJECT-TYPE
		       SYNTAX INTEGER
		       ACCESS read-only
		       STATUS mandatory
DESCRIPTION ""
		       ::= { ecsRLCStationLocate 1 }


	       ecsRLCNumbOfSLEntries OBJECT-TYPE
		       SYNTAX INTEGER
		       ACCESS read-only
		       STATUS mandatory
DESCRIPTION ""
		       ::= { ecsRLCStationLocate 2 }


	       ecsRLCSLDataBaseStatus OBJECT-TYPE
		       SYNTAX INTEGER {
			       changed(1),	--  DB has changed
			       unchanged(2),	--  DB has not changed
			       clear(3),	--  Clear the DB
			       full(4)		--  DB is full
		       }
		       ACCESS read-write
		       STATUS mandatory
DESCRIPTION ""
		       ::= { ecsRLCStationLocate 3 }

	       ecsRLCSLowFilterAddress OBJECT-TYPE
		       SYNTAX OCTET STRING
		       ACCESS read-write
		       STATUS mandatory
DESCRIPTION ""
		       ::= { ecsRLCStationLocate 4 }


	       ecsRLCSLhighFilterAddress OBJECT-TYPE
		       SYNTAX OCTET STRING
		       ACCESS read-write
		       STATUS mandatory
DESCRIPTION ""
		       ::= { ecsRLCStationLocate 5 }



-- ecs Station Locate DataBase

               ecsRLCStationLocateTable OBJECT-TYPE
                       SYNTAX  SEQUENCE OF ECSRLCStationLocateEntry
                       ACCESS  not-accessible
                       STATUS  mandatory
DESCRIPTION ""
                       ::= { ecsRLCStationLocate 6 }

               ecsRLCStationLocateEntry OBJECT-TYPE
                       SYNTAX  ECSRLCStationLocateEntry
                       ACCESS  not-accessible
                       STATUS  mandatory
DESCRIPTION ""
                       INDEX   { ecsRLCSLAddress }  
                       ::= { ecsRLCStationLocateTable 1 }

               ECSRLCStationLocateEntry ::= SEQUENCE {
		       ecsRLCSLAddress
			  OCTET STRING,
		       ecsRLCSLSlotIndex
			  INTEGER,
		       ecsRLCSLPortIndex
			  INTEGER,
		       ecsRLCSLStatus
			  INTEGER	       
    		    }

               ecsRLCSLAddress OBJECT-TYPE
                       SYNTAX OCTET STRING
                       ACCESS read-only
                       STATUS mandatory
 		       DESCRIPTION
 		       "The MAC Address for which one wishes to locate the
 			 slot and port." 
                       ::=  { ecsRLCStationLocateEntry 1 }

               ecsRLCSLSlotIndex OBJECT-TYPE
                       SYNTAX INTEGER
                       ACCESS read-only
                       STATUS mandatory
 		       DESCRIPTION
 		       "The slot number for this MAC address declared in 
 			ecsRLCStationAddress." 
                       ::=  { ecsRLCStationLocateEntry 2 }

               ecsRLCSLPortIndex OBJECT-TYPE
                       SYNTAX INTEGER
                       ACCESS read-only
                       STATUS mandatory
 		       DESCRIPTION
 		       "The port number for this MAC address declared in 
 			ecsRLCStationAddress." 
                       ::=  { ecsRLCStationLocateEntry 3 }


               ecsRLCSLStatus OBJECT-TYPE
                       SYNTAX INTEGER {
				 clear(1)	-- entry is deleted
		       }
                       ACCESS read-write -- actually write-only
                       STATUS mandatory
 		       DESCRIPTION
 		       "Writing clear(1) will clear the entry in the LinkBuilder ECS DataBase." 
                       ::=  { ecsRLCStationLocateEntry 4 }


-- ecs New or Changed Station Location DataBase

               ecsRLCNewStationLocateTable OBJECT-TYPE
                       SYNTAX  SEQUENCE OF ECSRLCNewStationLocateEntry
                       ACCESS  not-accessible
                       STATUS  mandatory
DESCRIPTION ""
                       ::= { ecsRLCStationLocate 7 }

               ecsRLCNewStationLocateEntry OBJECT-TYPE
                       SYNTAX  ECSRLCNewStationLocateEntry
                       ACCESS  not-accessible
                       STATUS  mandatory
DESCRIPTION ""
                       INDEX   { ecsRLCNewSLAddress }  
                       ::= { ecsRLCNewStationLocateTable 1 }

               ECSRLCNewStationLocateEntry ::= SEQUENCE {
		       ecsRLCNewSLAddress
			  OCTET STRING,
		       ecsRLCNewSLSlotIndex
			  INTEGER,
		       ecsRLCNewSLPortIndex
			  INTEGER	       
    		    }

               ecsRLCNewSLAddress OBJECT-TYPE
                       SYNTAX OCTET STRING
                       ACCESS read-only
                       STATUS mandatory
 		       DESCRIPTION
 		       "The MAC Address for which one wishes to locate the
 			 slot and port." 
                       ::=  { ecsRLCNewStationLocateEntry 1 }

               ecsRLCNewSLSlotIndex OBJECT-TYPE
                       SYNTAX INTEGER
                       ACCESS read-only
                       STATUS mandatory
 		       DESCRIPTION
 		       "The slot number for this MAC address declared in 
 			ecsRLCNewSLAddress." 
                       ::=  { ecsRLCNewStationLocateEntry 2 }

               ecsRLCNewSLPortIndex OBJECT-TYPE
                       SYNTAX INTEGER
                       ACCESS read-only
                       STATUS mandatory
 		       DESCRIPTION
 		       "The port number for this MAC address declared in 
 			ecsRLCNewSLAddress." 
                       ::=  { ecsRLCNewStationLocateEntry 3 }





                xecsDummyTable OBJECT-TYPE
                        SYNTAX  SEQUENCE OF ECSDummyEntry
                        ACCESS  not-accessible
                        STATUS  mandatory
 		       DESCRIPTION
 		       "A dummy table which allows management
 			of all tables (an snm bug)." 
                        ::= { lbecsXENDOFMIB 1 }

                ecsDummyEntry OBJECT-TYPE
                        SYNTAX  ECSDummyEntry
                        ACCESS  not-accessible
                        STATUS  mandatory
DESCRIPTION ""
                        INDEX   { ecsDummyIndex } 
                       ::= { xecsDummyTable 1 }
 
                 ECSDummyEntry ::= SEQUENCE {
 		       ecsDummyIndex    			
 			  INTEGER,
 		       ecsDummyValue
 			  INTEGER
 		      }

 		ecsDummyIndex OBJECT-TYPE
 			SYNTAX INTEGER
 			ACCESS read-only
 			STATUS mandatory
DESCRIPTION ""
 			::= { ecsDummyEntry 1 }

 		ecsDummyValue OBJECT-TYPE
 			SYNTAX INTEGER
 			ACCESS read-write
 			STATUS mandatory
DESCRIPTION ""
 			::= { ecsDummyEntry 2 }


-- Trap definition after RFC 1215 Conentions for defining Traps


-- generic traps for use with snmp  

--	      coldStart TRAP-TYPE
--		      ENTERPRISE linkBuilderECS
--		      DESCRIPTION
--		      "cold start trap"
--		      ::= 0

--             authenticationFailure TRAP-TYPE
--                     ENTERPRISE linkBuilderECS
--                     DESCRIPTION
--                     "authoricationFailure"
--                     ::= 4

--             enterpriseSpecific TRAP-TYPE
--                     ENTERPRISE linkBuilderECS
--                     DESCRIPTION
--                     "enterpriseSpecific trap"
--                     ::= 6


-- ecs enterprise specific traps  
			
             powerSupplyFailure TRAP-TYPE
                      ENTERPRISE  linkBuilderECS
 		      VARIABLES	  { ecsPSUStatus }
                      DESCRIPTION
                      "One of the PSUs has failed, the value of ecsPSUStatus is
 		       returned to indicate which PSU has failed."
                      ::= 0
			 
             fanFailure TRAP-TYPE
                       ENTERPRISE linkBuilderECS
                       DESCRIPTION
                       "A LinkBuilder ECS Fan has failed, requiring
 			immediate attenstion."
                       ::= 1
 
              configurationChanged TRAP-TYPE
                       ENTERPRISE linkBuilderECS
                       DESCRIPTION
                       "The LinkBuilder ECS configuartion has changed. Either a card has
 			been added or removed, a port disabled or enabled from the front
 			panel or a AUI port has been selected/deselected."
                       ::= 2

              portTrap TRAP-TYPE
                       ENTERPRISE linkBuilderECS
 		       VARIABLES { ecsInfoSlotIndex,
 				   ecsInfoPortIndex,
 				   ecsPortErrorState }
                       DESCRIPTION
                       "A port has partitioned/unpartitioned or has changed link state. The
 			values of ecsInfoSlotIndex and ecsInfoPortIndex are returned to
 			indicate the slot and port, the ecsPortErrorState is returned to
 			indicate the type or port error."
                       ::= 3
 

              resilientLinkTrap TRAP-TYPE
                       ENTERPRISE linkBuilderECS
 		       VARIABLES { ecsRLMainLinkSlot,
 				   ecsRLMainLinkPort,
 				   ecsRLStandbySlot,
 				   ecsRLStandbyPort,
 				   ecsRLActiveLink,
 				   ecsResLinkState }
                       DESCRIPTION
                       "The LinkBuilder ECS Resilient Link system has operated.
 			 The resilient link is returned to determine the action taken."
                       ::= 4
 

              rateTrap TRAP-TYPE
                       ENTERPRISE linkBuilderECS
 		       VARIABLES { ecsInfoSlotIndex,
 				   ecsInfoPortIndex,
 				   ecsPortErrorState }
                       DESCRIPTION
                       "A Guage threshold has been exceeded. The slot and port number
 			are given by the vakues if ecsInfoSlotIndex and ecsInfoPortIndex 
 			and the guage that has been exceeded is given by the value of 
 			ecsPortErrorState."
                       ::= 5
 

              stationlocateTrap TRAP-TYPE
                       ENTERPRISE linkBuilderECS
 		       VARIABLES { ecsRLCSLDataBaseStatus }
                       DESCRIPTION
                       "The Station Locate databse has either changed or has become
 			full. The particular condition is shown by the value of
 			ecsRLCSLDataBAseStatus returned."
                       ::= 6
 
              secureRLCTrap TRAP-TYPE
                       ENTERPRISE linkBuilderECS
 		       VARIABLES { ecsAgentSecureManagementStatus }
                       DESCRIPTION
                       "There has been access to the security menus from the front panel
 			menus. The value of ecsAgentSecureManagementStatus reports
 			whether the trap was generated beacuse the security menus were
 			entered, the secure password was violated or the security
 			configuration has been changed."
                       ::= 7
 
              secureRLCportTrap TRAP-TYPE
                       ENTERPRISE linkBuilderECS
 		       VARIABLES { ecsSecRLCSlotIndex,
 				   ecsSecRLCPortIndex,
 				   ecsSecRLCPortState,
 				   ecsSecRLCMACAddress }
                       DESCRIPTION
                       "A secure port has either detected an authorised port and taken
 			appropriate action or has learnt an authorised station on the
 			slot and port indicated."
                       ::= 8

END
