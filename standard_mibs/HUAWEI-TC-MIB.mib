-- ============================================================================
-- Copyright (C) 2014 by HUAWEI TECHNOLOGIES. All rights reserved.
--
-- Description: This module defines TEXTUAL-CONVENTION that is used by Huawei devices,
-- including HWFrameType, HWPCBType,HWSubPCBType, and HWPortType. The following talbe
-- lists the code area used by each product.

-- Reference:
-- Version: V5.56
-- History:


-- ============================================================================
	 HUAWEI-TC-MIB DEFINITIONS ::= BEGIN
		  IMPORTS
				Integer32,IpAddress, OBJECT-TYPE, MODULE-IDENTITY, OBJECT-IDENTITY,
				NOTIFICATION-TYPE
					 FROM SNMPv2-SMI
				TEXTUAL-CONVENTION,DateAndTime,MacAddress
					 FROM SNMPv2-TC
				ifEntry
					 FROM IF-MIB
				huawei
					 FROM HUAWEI-MIB;



		  huaweiTCMIB MODULE-IDENTITY
				LAST-UPDATED "201410221200Z"
				ORGANIZATION "Huawei Technologies Co.,Ltd."
				CONTACT-INFO
					 "Huawei Industrial Base
						Bantian, Longgang
						 Shenzhen 518129
						 People's Republic of China
						 Website: http://www.huawei.com
						 Email: support@huawei.com
					  "
				DESCRIPTION
					 "Huawei text conventions and common  defination."


		  --  Revision history MxUV800R016C00 add new mib
		  REVISION    "201410221200Z"
		  DESCRIPTION "V5.56,
							 Add: MA5811SH821MABC(145953),      -- Virtual frame H821MABC of MA5811S device.
							 Add: bnameHS35FDEM(155968),       -- 16G.FAST+VECTOR board of MA5811S FTTS device.
							 Add: bnameH835FDEM(155969),       -- Master board of MA5811S-DE16 FTTS device.
							 "


		  --  Revision history RPS add new mib
		  REVISION    "201410201200Z"
		  DESCRIPTION "V5.55,
							Add: fnameCPF104(786434),             --The RPS's with BT-C Power Frame backplane.
							Add: fnameCFS02(786435),              --The RPS's with BT-C Fan Frame.
							Add: fnameETP4830-A1(786436),         --The RPS's with AC-DC System Frame.
							Add: fnameETP4890-A2(786437),         --The RPS's with AC-DC System Frame.
							Add: fnameETP48150-A3(786438),        --The RPS's with AC-DC System Frame.
							Add: fnameCPF104(786439),             --The RPS's with RTF-V Power Frame backplane.


							Add: bnameCPF104Power(786637),        --BT-C Power input module board,with 0 port
							Add: bnameCCM08B(786638),             --BT-C Up converter module board,with 8 DC output ports
							Add: bnameRCM08(786639),              --BT-C Down converter module board,with 12 DC input ports
							Add: bnameCFS02Power(786640),         --BT-C Power input module board,with 0 port
							Add: bnameCFS02Monitor(786641),       --BT-C Fan module board,with 3 fan ports
							Add: bnameETP4830-A1Power(786642),    --BT-C AC-DC System monitor input module board,with 0 port
							Add: bnameETP4890-A2Power(786642),    --BT-C AC-DC System monitor input module board,with 0 port
							Add: bnameETP48150-A3Power(786644),   --BT-C AC-DC System monitor input module board,with 0 port
							Add: bnameSMU01B(786645),             --AC-DC System monitor Monitoring module board
							Add: bnameSMU01C(786657),             --AC-DC System monitor Monitoring module board
							Add: bnameR4830G1(786646),            --AC-DC System Power Supply Unit
							Add: bnameR4830N2(786647),            --AC-DC System Power Supply Unit
							Add: bnameR4815G1(786648),            --AC-DC System Power Supply Unit
							Add: bnameR4815N1(786649),            --AC-DC System Power Supply Unit
							Add: bnameCFS01Power(786650),         --RTF-C Power input module board,with 0 port
							Add: bnameCVM02(786651),              --RTF-V Up converter module board,with 8 DC output ports
							Add: bnameCFS01Power(786652),         --RTF-V Power input module board,with 0 port
							Add: bnameRPF106Power(786653),        --RTF-V Power input module board,with 0 port
							Add: bnameRMU01(786654),              --RTF-V Monitoring module board,with 0 port
							Add: bnameRFS01(786655),              --RTF-V Fan module board,with 3 fan ports
							Add: bnameRVM04(786656),              --RTF-V Down converter module board,with 12 DC input ports
							"

			--  Revision history DC add new mib
		  REVISION    "201410161200Z"
		  DESCRIPTION "V5.54,
							Add: fnameCE681048S4QLI(688140),          -- CloudEngine CE6810-48S4Q-LI Switch (48-Port 10GE SFP+,4-Port 40GE QSFP+)
							Add: fnameCE681048SLI(688141),            -- CloudEngine CE6810-48S-LI Switch (48-Port 10GE SFP+)
							Add: fnameCE12804S(688142),               -- CloudEngine 12800S,CE01PBK04AS,CE12804S Power Backplane,1*1
							Add: fnameCE12808S(688143),               -- CloudEngine 12800S,CE01BAK08AS,CE12808S Backplane A,1*1
							Add: fnameCE685048S6QHI(688144)           -- CloudEngine CE6850-48S6Q-HI Switch (48-Port 10GE SFP+,6-Port 40GE QSFP+)
							Add: bnameCEL48GTEF(688187),              -- Manufactured Board,iCE,CE-L48GT-EF,48-Port 10/100/1000BASE-T Interface Card(EF,RJ45)-1*1
							Add: bnameCE685048S6QHI(688189),          -- CloudEngine 6800,CE6850-48S6Q-HI Switch(48-Port 10GE SFP+,6-Port 40GE QSFP+)
							Add: bnameCEMPUAS(688190),                -- Manufactured Board,CloudEngine 12800S,CE-MPUA-S
							Add: bnameCEL48XTEC(688191),              -- Manufactured Board,CloudEngine 12800,CE-L48XT-EC,1*1
							Add: bnameCEL12CFEG(688192),              -- Manufactured Board,CloudEngine 12800,CE-L12CF-EG,12-Port-100GE Interface Card(EG,CFP2),1*1
							Add: bnameCEFWA(688193),                  -- Manufactured Board,CloudEngine 12800,CE-FWA,Fire Wall Card A,1*1
							Add: bnameCEL08CCEC(688194),              -- Manufactured Board,CloudEngine 12800,CE-L08CC-EC,1*1
							Add: bnameCEL24LQEC1(688195),             -- Manufactured Board,CE-L24LQ-EC1
							Add: bnameCESFUBS(688196),                -- Manufactured Board,CloudEngine 12800S,CE-SFUB-S
							Add: bnameCESFUCS(688197),                -- Manufactured Board,CloudEngine 12800S,CE-SFUC-S,CE-SFUC-S,1*1
							Add: addentnameCMU(688128),               -- CMU  Module
			  "
		  --  Revision history MxUV8R15C00 add new mib
			REVISION    "201408301200Z"
		  DESCRIPTION "V5.50,
		  add by dinglingfeng 20140630
					 Add:  bnameE8000EKW51ESPU(16748544),        --SPU Board ,Service Processing Unit
					 Add:  bnameE8000EDCU(16748545),         --DCU Board ,Detection and Clean Unit
					 Add:  bnameE8000ESUP3SPUA02(16748546),          --Service Processing Unit,with HS General Security Platform Software
					 Add:  bnameE8000ECR52LPUKD1(16748547),     --Flexible Card Line Processing Unit(LPUF-21,2 sub-slots) B
					 Add:  bnameE8000ESUP3SPUA02IPS(16748548),  --IPS Service Processing Unit,with HS General Security Platform Software
					 Add:  bnameE8000EKW51ESPUIPS(16748549),      --IPS SPU Board ,Service Processing Unit
		Add:  bnameE8000ESU91SPUC(16748550),      --Eudemon8000E-X,SU91SPUC,X3 Service Processiong Unit(Base Board),with HS General Security Platform Software
		Add:  bnameE8000ESU91SPUD(16748551),      --Eudemon8000E-X,SU91SPUD,X8&X16 Service Processiong Unit(Base Board),with HS General Security Platform Software
					 Add:  bnameE8000ESU91SPUC01(16748552),    --Eudemon8000E-X,SU91SPUC01,40G X3 Firewall Service Processing Unit ,with HW General Security Platform Software,include SPUC and 1*SPCC01
		Add:  bnameE8000ESU91SPUC02(16748553),    --Eudemon8000E-X,SU91SPUC02,20G X3 Firewall Service Processing Unit(oversea),with HW General Security Platform Software,include SPUC and 1*SPCB02
		Add:  bnameE8000ESU91SPUC03(16748554),    --Eudemon8000E-X,SU91SPUC03,60G X3 Firewall Service Processing Unit ,with HW General Security Platform Software
		Add:  bnameE8000ESU91SPUD01(16748555),    --Eudemon8000E-X,SU91SPUD01,40G X8&X16 Firewall Service Processing Unit ,with HW General Security Platform Software,include SPUD and  1*SPCC01
		Add:  bnameE8000ESU91SPUD02(16748556),    --Eudemon8000E-X,SU91SPUD02,80G X8&X16 Firewall Service Processiong Unit,with HW General Security Platform Software,include SPUD and 1*SPCB01
		Add:  bnameE8000ESU91SPUD03(16748557),    --Eudemon8000E-X,SU91SPUD03,20G X8&X16 Firewall Service Processing Unit(oversea),with HW General Security Platform Software,include SPUD and 1*SPCB02
					 Add:  bnameE8000ESU91SPUC04(16748570),    --Eudemon8000E-X,SU91SPUC04,40G X3 Firewall Service Processing Unit ,Double CPUs,with HW General Security Platform Software,include SPUC and 1*SPCB04
					 Add:  bnameE8000ESU91SPUD05(16748571),    --Eudemon8000E-X,SU91SPUD05,40G X8&X16 Firewall Service Processing Unit ,Double CPUs,with HW General Security Platform Software,include SPUD and  1*SPCB04
					 Add:  bnameE8000ESU91LPUF100CA00(16748572),	--Eudemon8000E-X,SU91LPUF100CA00,Flexible Card Line Processing Unit(LPUF-101,4 sub-slots),with HW General Security Platform Software
					 Add:  bnameE8000ESU91LPUF100CA0(16748573),	--Eudemon8000E-X3,SU91LPUF100CA01,X3 Flexible Card Line Processing Unit(LPUF-100,4 sub-slots),with HW General Security Platform Software
					 Add:  bnameE8000ESU91LPUI100CA00(16748574),	--Eudemon8000E-X,SU91LPUI100CA00,10-Port 10GBase LAN/WAN-SFP+ Integrated Line Processing Unit (LPUI-100) ,with HW General Security Platform Software
					 Add:  bnameE8000ESU91E1NC00(16748575),	--Eudemon8000E-X,SU91E1NC00,1-Port 100GBase-CFP Integrated Line Processing Unit (LPUI-101),with HW General Security Platform Software
					 Add:  bnameEudemon8000ESU91EDXFB0(16748576),	--Eudemon8000E-X,SU91EDXFB0,16-Port 10GBase LAN-SFP+ Integrated Line Processing Unit (LPUI-100) ,with HW General Security Platform Software
					 Add:  bnameEudemon8000ESU91E4XFA0(16748577),	--Eudemon8000E-X,SU91E4XFA0,4-Port 10GBase LAN-SFP+ Flexible Card(P100,1/4wide,Occupy one sub-slots)
					 Add:  bnameEudemon8000ESU91LBXF0(16748578),	--Eudemon8000E-X,SU91LBXF0,12-Port 10G Base LAN/WAN-SFP+ Flexible Card A(P120-A)

					 Add:  subbnameEudemon8000ECR52E1XXT0(16748544), --CR52E1XX0,1*10GBase LAN-XFP Optical Interface LPU A
					 Add:  subbnameEudemon8000ECR52W1XXT0(16748545), --CR52W1XX0,1*10GBase WAN-XFP Optical Interface LPU A
					 Add:  subbnameEudemon8000ECR52P1XXT0(16748546), --CR52P1XX0,1*OC-192c/STM-64c POS-XFP Optical Interface LPU A
					 Add:  subbnameEudemon8000ECR52R1XF(16748547),   --CR52R1XX0,1*OC-192c/STM-64c RPR-XFP Optical Interface LPU A
					 Add:  subbnameEudemon8000ECR52E5GF(16748548),   --CR52E5GF,5-port GbE SFP Optical Interface LPU G
					 Add:  subbnameEudemon8000ECR52C8E10(16748549),  --CR52C8E10,8-Port Channelized E1-RJ45 Flexible Service Interface Card
					 Add:  subbnameEudemon8000ECR52C8T10(16748550),  --CR52C8T10,8-Port Channelized T1-RJ45 Flexible Service Interface Card
					 Add:  subbnameEudemon8000ECR52C1CF1(16748551),  --CR52C1CF1,1 port Channelized OC-3/STM-1 Flexible Service Interface Card
					 Add:  subbnameEudemon8000ECR52L1XX0(16748552),  --1-port 10GBase WAN/LAN XFP Flexible Interface Daughter Card
					 Add:  subbnameEudemon8000ECR52EBGF0(16748553),  --12-port 100/1000Base-X SFP Flexible Interface Daughter Card
					 Add:  subbnameEudemon8000ECR52EBGE0(16748554),  --12-port 10/100/1000Base-TX RJ45 Flexible Interface Daughter Card
					 Add:  subbnameEudemon8000ECR52P1XXBZ0(16748555),--1 port OC-192c/STM-64c POS-XFP Flexible Card
		Add:  subbnameEudemon8000ESU91L4XX00(16748556),	   --SU91L4XX00 4 Port 10G Base WAN/LAN-XFP
			  Add:  subbnameEudemon8000ESU91L4XX01(16748557),	   --SU91L4XX01 4 Port 10G Base LAN/LAN-XFP
			  Add:  subbnameEudemon8000ESU91SPCB02(16748558),	   --Eudemon8000E-X,SU91SPCB02,20G Firewall Performance Expansion Card(oversea),with HS General Security Platform Software
			  Add:  subbnameEudemon8000ESU91SPCC01(16748559),	   --Eudemon8000E-X,SU91SPCC01,40G Firewall Processing Card,with HS General Security Platform Software
			  Add:  subbnameEudemon8000ESU91SPCB01(16748560),	   --Eudemon8000E-X,SU91SPCB01,80G Firewall Processing card,with HS General Security Platform Software
			  Add:  subbnameEudemon8000ESUP5SPCC(16748561),          --SUP,SUP5SPCC,Service Processing Card,1*1
					 Add:  subbnameEudemon8000ESUP5SPCA(16748562),          --SUP,SUP5SPCA,Service Processing Card,1*1

					 Add:  subbnameEudemon8000ESU91SPCB04(16748572),	--Eudemon8000E-X,SU91SPCB04,40G Firewall Processing card,Double CPUs,with HW General Security Platform Software
					 Add:  subbnameEudemon8000ESU91IPSC01(16748573),	--Eudemon8000E-X,SU91IPSC01,IPS Service Processing Card, with HW General Security Platform Software
					 Add:  subbnameEudemon8000ESU91L5XXA0(16748574),	--Eudemon8000E-X,SU91L5XXA0,5-Port 10GBase LAN/WAN-SFP+ Flexible Card A(P101,1/2wide,Occupy two sub-slots)
					 Add:  subbnameEudemon8000ESU91EFGFA0(16748575),	--Eudemon8000E-X,SU91EFGFA0,24-Port 100/1000Base-X-SFP Flexible Card(P100,1/2wide,Occupy two sub-slots)
					 Add:  subbnameEudemon8000ESU91E1MCB(16748576),	--Eudemon8000E-X,SU91E1MCB,1-Port 40GBase LAN CFP Flexible Card(P100,1/2wide,Occupy two sub-slots)
					 Add:  subbnameEudemon8000ESU91E4XFA0(16748577),	--Eudemon8000E-X,SU91E4XFA0,4-Port 10GBase LAN-SFP+ Flexible Card(P100,1/4wide,Occupy one sub-slots)
					 Add:  subbnameEudemon8000ESU91LBXF0(16748578),	--Eudemon8000E-X,SU91LBXF0,12-Port 10G Base LAN/WAN-SFP+ Flexible Card A(P120-A)
					 Add:  bnameSUA2MPUA(16719976),          --USG6600 Main Processing Unit
					 Add:  bnameSUA2CSPUA(16719977),         --USG6600 Content Security Process Unit
					 Add:  bnameSUA2X2G8(16719978),          --USG6600 2*10GE Optical Ports+8GE Electric Ports Interface Card
					 Add:  bnameSUA2E2XSF(16719979),         --USG6600 2*10GE Optical Ports Interface Card
					 Add:  bnameSUE3E8GF(16719980),          --USG6600 8GE Optical Ports Interface Card
					 Add:  bnameSUE3E4BY(16719981),          --USG6600 4GE Electric Ports Bypass Card
					 Add:  bnameSUE3E8GE(16719982),          --USG6600 8GE Electric Ports Interface Card
					 Add:  bnameSUE5MPUA(16719983),          -- USG3600 Main Processing Unit
					 Add:  bnameSUE5DSBB(16719984),          -- USG3600 HD Switch Board
					 Add:  bnameSUA1MPUB(16719985),          -- USG3600 1U Main Processing Unit Board
					 Add:  bnameSUE1EPSEC(16719986),         -- USG3600 The state password encryption Daughter card
					 Add:  bnameSUE5FIBA(16719987),	  --Fixed Interface Board
					 Add:  bnameET1D2IPS0S00(16719988),	  -- IPS Module A,with HW General Security Platform Software
					 Add:  bnameET1D2FW00S00(16719989),	  -- NGFW Module A,with HW General Security Platform Software
					 Add:  bnameET1D2FW00S01(16719990),	  -- NGFW Module B,with HW General Security Platform Software
					 Add:  bnameET1D2FW00S02(16719991),	  -- NGFW Module C,with HW General Security Platform Software
					 Add:  bnameLE1D2FW00S01(16719992),	  -- NGFW Module B,with HW General Security Platform Software
					 Add:  bnameSUE6MPUA(16719993),	  -- Manufactured Board,USG6600,SUE6MPUA,Main Processing Unit Board
					 Add:  bnameSUE3MPUA(16719994),	  -- Manufactured Board,USG6300,SUE3MPUA,Main Processing Unit Board
					 Add:  bnameSUE3BPKA(16719995),	  -- USG6300,SUE3BKPA,1U BackPlane Board
					 "

		  --  Revision history MxUV8R15C00 add new mib
			REVISION    "201401071200Z"
		  DESCRIPTION "V5.37,
							 Merage VRP and IAS 'S mib together.
							 "
			--  Revision history RPS add new mib
		  REVISION    "201406231200Z"
		  DESCRIPTION "V5.36,
							Add: fnameCPF318(786432),       --The RPS's Power Frame backplane.
							Add: fnameCFS01(786433),        --The RPS's Fan Frame.

							Add: bnameCMU01(786632),              --Monitoring module board,with 0 port.
							Add: bnameCFS01(786633),              --Fan module board,with 3 fan ports
							Add: bnameCPF318Power(786634),        --Power input module board,with 0 port
							Add: bnameCCM08(786635),              --Up converter module board,with 8 DC output ports
							Add: bnameRC12S(786636),              --Down converter module board,with 12 DC input ports

							Add: fanPort(786932),                   --Fan module fan port
							Add: dcoutputPort(786933),              --Up converter module DC output port
							Add: dcinputPort(786694),               --Down converter module DC input port
							"
		  --  Revision history MxUV8R15C00 add new mib
		  REVISION    "201406161200Z"
		  DESCRIPTION "V5.35,
							Add: fnameMA5694SCLKH821MABC(147455), -- Virtual frame H821MABC of MA5694S  GE 1588V2 SLAVE DOCK device.
							Add: bnameHS22GE3A(155984),           -- 3GE LAN board of the MA5694S.
							"

		  --  Revision history MA5800V1R15C10 add new mib
		  REVISION    "201406121200Z"
		  DESCRIPTION "V5.34,
							Add: bnameH801X2CK(146078),         --10GE synchronized Ethernet interface board
							"

		  --  Revision history MxUV8R15C10 add new mib
			REVISION    "201406111400Z"
		  DESCRIPTION "V5.33,

							 Add: frameMA5611SDE48(DT)(143377) to frameMA5611SDE48-A(DT)(143377)
							 Add: bnameCCM(155982),       -- 48-channel Vectoring VDSL2 + POTS COMBO service board
							 Add: bnameVCP(155983),       -- 64-channel Vectoring VDSL2 + SPL service board
							 "
		  --  Revision history MxUV8R15C10 add new mib
		  REVISION    "201406101200Z"
		  DESCRIPTION "V5.32,
							 Add: bnameH822CCKRC(155980),        -- Master board of MA5633(sd5130) device.
							 Add: bnameHS33CDAC(155981),         -- DOCSIS virtual board of MA5633.
							 "
		  --  Revision history MA5800V1R15C00 add new mib
		  REVISION    "201406061200Z"
		  DESCRIPTION "V5.31,
							Add: bnameH802SCUB(148011),         --  control board of MA5600T
							Add: bnameH806CAME(146077),         -- 48-channel ADSL combo service board
							"

		  --  Revision history MA5800V1R15C00 add new mib
		  REVISION    "201406041200Z"
		  DESCRIPTION "V5.30,
							Add: fnameMA5800H901BPLB(148501),     -- Backplane of the MA5800
							Add: bnameH901MPLA(148501),         --  control board of MA5800
							Add: bnameH901MPLB(148502),         --  control board of MA5800
							Add: bnameH901XGHD(148521),         --  8*10G GPON board of MA5800
							Add: bnameH901GPHF(148522),         --  16*GPON board of MA5800
							Add: bnameH901OGHK(148523),         --  48 P2P board of MA5800
							Add: bnameH901NXED(148524),         --  8*10GE board of MA5800
							Add: bnameH901OXHD(148525),         --  8*10GE extend board of MA5800
							Add: bnameH901PILA(148526),         --  Power board of MA5800
							Add: bnameH901CIUA(148527),         --  GPIO board of MA5800
							Add: subbnameH901CKUA(148501),          -- Clock subboard of MA5800 H901MPLB
							 "
			--  Revision history MA5600TV8R15C00 add new mib
		  REVISION    "201405151200Z"
		  DESCRIPTION "V5.29,
							 Add: bnameH801MPWE(146076),          -- Power board of MA5608T.
							 "

		  --  Revision history MxUV8R15C00 modified mib
			REVISION    "201405061200Z"
		  DESCRIPTION "V5.28,
							 Add: bnameH831EPFF(155965),          -- 2 GE Vitual Board of MA5612.
							 Add: bnameH82BDVJM(155966),          -- Master board of MA5611S-AE08(sd5130) FTTS device.
							 Add: bnameHS2BDVJM(155967),          -- 8 VDSL2 board of MA5611S-AE08(sd5130) FTTS device.
							 Add: frameMA5611SAE08(561221),       -- Virtual frame MA5611S-AE08 of MA5611S(sd5130) FTTS device.
							 "

		  --  Revision history MxUV8R15C00 add new mib
			REVISION    "201402201400Z"
		  DESCRIPTION "V5.27,
							 Modify: frameMA5611SCE48(561206) to frameMA5611SDE48-TELUS(561206).
							 Modify: frameMA5611SDE48(561193) to frameMA5611SDE48-A(561193)
							 "

		  --  Revision history MxUV8R15C00 add new mib
			REVISION    "201402171700Z"
		  DESCRIPTION "V5.26,
							 Add: bnameH823UPVBP(155976),         -- Master board of MA5611S-AE16(sd5130) FTTS device for Oman.
							 Add: bnameHS23UPVBP(155977),         -- 16 VDSL2 board of MA5611S-AE16(sd5130) FTTS device for Oman.
							 Add: bnameH826BVUP(155978),          -- Master board of MA5611S-DE16(sd5130) FTTS device for BT.
							 Add: bnameHS26BVUP(155979),          -- 16 VDSL2 board of MA5611S-DE16(sd5130) FTTS device for BT.
							 "

		  --  Revision history MxUV8R15C00 add new mib
			REVISION    "201401291605Z"
		  DESCRIPTION "V5.25,
							 Add: frameMA5611SCE48(561206),  -- Virtual frame MA5611S-CE48 of MA5611S(sd5103) FTTS device for TELUS.
							 Add: frameMA5611SAE16(561207),  -- Virtual frame MA5611S-AE16 of MA5611S(sd5130) FTTS device for Oman.
							 Add: frameMA5611SDE16(561208),  -- Virtual frame MA5611S-DE16 of MA5611S(sd5130) FTTS device for BT.
							 "

		  --  Revision history MxUV8R15C00 add new mib
			REVISION    "201401071200Z"
		  DESCRIPTION "V5.24,
							 Add:     bnameH831EDTB(155975),          -- E1 board of MA5616 for CCUE and CCUD.
							 "

		  --  Revision history MxUV8R15C00 add new mib
			REVISION    "201312121200Z"
		  DESCRIPTION "V5.23,
							 Add:     fnameMA5633H821MABCS(561197),   -- Virtual frame H821MABCS of mini MA5633(sd5130) device.
							 Add:     bnameH822CCKRB(155973),         -- Master board of mini MA5633(sd5130) device.
							 Add:     bnameHS33CDAB(155974),          -- DOCSIS virtual board of mini MA5633.
							 Add:     subbnameH831UP2E(155952),       -- Auto adapt upstream subboard of MA5633, It supports EQAM.
							 Add:     subbnameH831UP2F(155953),       -- Auto adapt upstream subboard of MA5633, It not supports EQAM.
							 Add:     subbnameHS21PWBB(155954),       -- Virtual power subboard of MA5633.
							 Add:     subbnameHS21MIXB(155955),       -- Virtual mixer subboard of MA5633.
							 "

		  --  Revision history R15C00 add new mib
			REVISION    "201310161200Z"
		  DESCRIPTION "V5.22,
							 Add:     bnameH80XVPG(146138),       -- support vector board of MA5600T.
							 Add:     bnameH806CCPE(146139),      -- 64-channel POTS(combo) + Vectoring board of MA5600T device.
							 Add:     bnameH801XGBD(146141),      -- 8 ports 10G GPON board.
							 Add:     bnameH803XEBD(146142),      -- 8 ports 10G EPON board.
							 Add:     bnameH805EPFD(146143),      -- 16EPON board.
							 Add:     bnameH802GPMD(146144),      -- 8GPON board.
							 Add:     bnameH805GPFD(146145),      -- 16GPON board.
							 Add:     bnameH802XEBD(146146),      -- 8 ports 10G EPON board.
							 Add:     bnameH802SCUH(148009),      -- control board of MA5600T.
							 Add:     bnameH802SCUV(148010),      -- control board of MA5600T.
							 "

		  --  Revision history R312C91 add new mib
			REVISION    "201309161200Z"
		  DESCRIPTION "V5.21,
							 Add:     fnameMA5611SAE-48(561205),  -- Virtual frame H831MABC of MA5611S-AE48 device.
							 Modify: bnameH831PAVD(155919),       -- Double DC Power board H832PDVAA of  the  MA5616.
							 Modify: bnameH831PAVDA(155937),      -- Double DC Power board H831PAVDA of  the  MA5616, witch vector vp subboard.
							 Modify: bnameH831CCLF(155952),       -- Master board of MA5678(sd5130)device.
						  "
	--  Revision history R313C10 add new mib
		  REVISION    "201308151200Z"
		  DESCRIPTION "V5.20,
							 Modify: bnameH82DVCMM(155949),     -- Master board of MA5611S-DE48(sd5130) FTTS device.
							 Modify: bnameHS2DVCMM(155962),     -- 48 VDSL + Vectoring board of MA5611S-DE48(sd5130) device.
							 "

		  --  Revision history R313C10 add new mib
		  REVISION    "201308031200Z"
		  DESCRIPTION "V5.19,
							 Add: frameMA5611SDE48(561193),  -- Virtual frame frameMA5611S-DE48 of MA5611S(sd5130) device.
							 Add: bnameH82DVCMM2(155949),    -- Master board of MA5611S-DE48(sd5130) FTTS device.
							 Add: bnameHS2DVCMM2(155962),    -- 48 VDSL + Vectoring board of MA5611S(sd5130) device.
							 Modify:fnameMA5694SDSLH831MABC to fnameMA5694SDSLH821MABC.
							 Modify:fnameMA5694SPONH831MABC to fnameMA5694SPONH821MABC.
							 "

		  --  Revision history R313C10 add new mib
			REVISION    "201307041200Z"
		  DESCRIPTION "V5.18,
							 Add:     veiPort(805),                             -- Vei port of board NLV.
							 Add:     vdslNNIPort(806),                         -- VDSL upstream port.
						  "

		  --  Revision history R13C00 add new mib
			REVISION    "201307041200Z"
		  DESCRIPTION "V5.17,
							 Add:     fnameMA5600H802Mabc(145952),     -- Backplane of the P300 broadband master Frame: H802MABC.
						  "

				--  Revision history R13C10 add new mib
			REVISION    "201306081200Z"
		  DESCRIPTION "V5.15,
							 Add:     bnameH801SPUC(155955),        -- Interface board.
							 Add:     bnameH802OPGE(146075),        -- H802OPGE BOARD
							 Add:     subbnameH801CKMD(888891),     -- Clock subboard.
							 Add:     bnameSHG(143447),             -- P300 32-channel G.SHDSL board of the SHG series.
						  "

		  --  Revision history R312C91 add new mib
			REVISION    "201306071200Z"
		  DESCRIPTION "V5.15,
							 Add:     fnameMA5611SDE-48(561204),              --  Virtual frame H831MABC of MA5611S-DE48 north Americal device.
							 Add:     bnameH82BCVMM(155972),                  --  Master board of MA5611S-DE48 north Americal device.
							 Modidy:  fnameMA5611S-AE16(561191),              --  Virtual frame H831MABC of MA5611S-AE16(sd5130) device.
						  "


		  --  Revision history R13C10 add new mib
		  REVISION    "201305150000Z"
		  DESCRIPTION "V5.14,
							 Add:     fnameMA5694SDSLH821MABC(561199), -- Virtual frame H821MABC of MA5694S  DSL DOCK device.
							 Add:     fnameMA5694SPONH821MABC(561203), -- Virtual frame H821MABC of MA5694S  PON DOCK device.
							 Add:     bnameH822CC3G(155957),         --  DSL DOCK for MA5694S device.
							 Add:     bnameHS31EPFB(155959),         --  3GE LAN board of the MA5694S.
							 Add:     subbnameH831VD4A(155951),      -- VD4A  Subboard for MA5694S.
							 Add:     bnameH822UPWC(155970),         --  PON DOCK for MA5694S device.
							 Add:     bnameHS22GE4A(155971),         --  4GE LAN board of the MA5694S.

							 Add:     bnameHS22EPGE(155961),         -- Virtual 24GE board of the MA5821.
							 Add:     bnameH836VPAA(155963),      -- VPA  Subboard for MA5616.
							 Add:     bnameH832PDNAA(155964),        -- Power board for NLV  of the MA5616.
							 Add:     subbnameVPA(155950),           -- VECTOR Subboard VPA."

		  --  Revision history R13C00 add new mib
			REVISION    "201305081200Z"
		  DESCRIPTION "V5.13,
							 Add:     fnameMA5633(147527),           --  MDU device MA5633 used as remote frame.
						  "

		  --  Revision history R313C00 add new mib
		  REVISION    "201305020000Z"
		  DESCRIPTION "V5.12,
							 Add: fnameMA5898H831Mabl(561202),  -- Backplane of the MA5898 master Frame: H831MABL.
										"

		  --  Revision history R13C00 add new mib
		  REVISION    "201303220000Z"
		  DESCRIPTION "V5.11,
							 Add:     bnameH801MCUE(148006),         --  MA5608T control board H801MCUE.
							 Add:     bnameH801GPMD(148007),         --  gpon board of the MA5600T.
							 Add:     bnameH801SCUV(148008),         --  MA5600T control board H801SCUV.
							 Add:     subbnameH801CPCC(204934),      --  Clock subboard for the H801MCUE board."

		  --  Revision history R313C00 add new mib
		  REVISION    "201303210000Z"
		  DESCRIPTION "V5.10,
							 Add: fnameMA5633H821Mabco(561192),  -- Virtual frame H821MABCO of MA5633(sd5130) device.
			"

	--  Revision history UA5000V100R019C07 add new mib
		  REVISION    "201303190000Z"
		  DESCRIPTION "V5.09,
							 Add:     bnameH601XP1A(204880),           -- UA5000 XPON board which unites Broadband and narrowband has 5*FE Electric Ports, 4*E1 Ports, 2*GE Optical Ports, 1GE Electric Port and 1GPON Port
										"

		  --  Revision history R313C00 add new mib
		  REVISION    "201303150000Z"
		  DESCRIPTION "V5.08,
							 Add: fnameMA5622A-16(561200),    -- Virtual frame H831MABC of MA5622A-16 device.
							 Add: fnameMA5622A-8(561201),     -- Virtual frame H831MABC of MA5622A-8 device.
			"

		  --  Revision history R313C00 add new mib
		  REVISION    "201303140000Z"
		  DESCRIPTION "V5.07,
							 Add: fnameMA5818H831Maba(561195),  -- Backplane of the MA5818 master Frame: H831MABA.
							 Add: fnameMA5818H831Mabb(561196),  -- Backplane of the MA5818 master Frame: H831MABB.
										"
		  --  Revision history R312C00 add new mib
		  REVISION    "201302280000Z"
		  DESCRIPTION "V5.06,

				Add:  fnameSU1Z21UHA(16715776),                   -- USG2200,SU1Z21UHA,USG2210 Host
							 Add:  fnameSU1Z21UHB(16715777),                   -- USG2200,SU1Z21UHB,USG2220 Host
							 Add:  fnameSU1Z21UHC(16715778),                   -- USG2200,SU1Z21UHC,USG2230 Host
							 Add:  fnameSU1Z21UHD(16715779),                   -- USG2200,SU1Z21UHD,USG2250 Host
							 Add:  fnameSU1Z22UHA(16715780),                   -- USG2200,SU1Z22UHA,USG2210 Host,HuaweiSymantec Overseas
							 Add:  fnameSU1Z22UHB(16715781),                   -- USG2200,SU1Z22UHB,USG2220 Host,HuaweiSymantec Overseas
							 Add:  fnameSU1Z22UHC(16715782),                   -- USG2200,SU1Z22UHC,USG2230 Host,HuaweiSymantec Overseas
							 Add:  fnameSU1Z22UHD(16715783),                   -- USG2200,SU1Z22UHD,USG2250 Host,HuaweiSymantec Overseas
							 Add:  fnameFWGZ21UHA(16715784),                   -- Quidway Eudemon,FWGZ21UHA,E200E-C Host
							 Add:  fnameFWGZ21UHD(16715785),                   -- Quidway Eudemon,FWGZ21UHD,E200E-F Host
							 Add:  fnameSRGZ2020(16715786),                    -- SRG20 Secure Routing Gateway,SRGZ2020,SRG20-20 AC Host
							 Add:  fnameSRGZ2021(16715787),                    -- SRG20 Secure Routing Gateway,SRGZ2021,SRG20-21 AC Host
							 Add:  fnameSRGZ2030(16715788),                    -- SRG20 Secure Routing Gateway,SRGZ2030,SRG20-30 AC Host
							 Add:  fnameSRGZ2031(16715789),                    -- SRG20 Secure Routing Gateway,SRGZ2031,SRG20-31 AC Host
							 Add:  fnameSRGZ2020IE(16715790),                  -- SRG20 Secure Routing Gateway,SRGZ2020IE,SRG20-20 AC Host
							 Add:  fnameSRGZ2021IE(16715791),                  -- SRG20 Secure Routing Gateway,SRGZ2021IE,SRG20-21 AC Host
							 Add:  fnameSRGZ2030IE(16715792),                  -- SRG20 Secure Routing Gateway,SRGZ2030IE,SRG20-30 AC Host
							 Add:  fnameSRGZ2031IE(16715793),                  -- SRG20 Secure Routing Gateway,SRGZ2031IE,SRG20-31 AC Host
							 Add:  fnameSU0Z11UHB(16715794),                   -- USG2100-SU0Z11UHB-USG2130 Host,HuaweiSymantec Overseas
							 Add:  fnameSU0Z13UHB(16715795),                   -- USG2100-SU0Z13UHB-USG2160 Host,HuaweiSymantec Overseas
							 Add:  fnameSRGZ23UHT(16715796),                   -- SRG3260,SRGZ23UHT,SRG3260 Host,with HS General Security Platform Software
							 Add:  fnameSU2Z12UAH(16715797),                   -- USG5100,SU2Z12UAH,USG5120 AC Host,with HS General Security Platform Software
							 Add:  fnameSU2Z12UDH(16715798),                   -- USG5100,SU2Z12UDH,USG5120 DC Host,with HS General Security Platform Software
							 Add:  fnameSU2Z13UHT(16715799),                   -- USG5100,SU2Z13UHT,USG5150 Host,with HS General Security Platform Software
							 Add:  fnameSU2Z22UAH(16715800),                   -- USG5100,SU2Z22UAH,USG5120BSR AC Host,with HS General Security Platform Software
							 Add:  fnameSU2Z22UDH(16715801),                   -- USG5100,SU2Z22UDH,USG5120BSR DC Host,with HS General Security Platform Software
							 Add:  fnameSU2Z23UHT(16715802),                   -- USG5100,SU2Z23UHT,USG5150BSR Host,with HS General Security Platform Software
							 Add:  fnameSRGZ12UAH(16715803),                   -- SRG3230,SRGZ12UAH,SRG3230 AC Host,with HS General Security Platform Software
							 Add:  fnameSRGZ22UAH(16715804),                   -- SRG3240,SRGZ22UAH,SRG3240 AC Host,with HS General Security Platform Software
							 Add:  fnameSRGZ22UDH(16715805),                   -- SRG3240,SRGZ22UDH,SRG3240 DC Host,with HS General Security Platform Software
							 Add:  fnameSRGZ13UHT(16715806),                   -- SRG3250,SRGZ13UHT,SRG3250 Host,with HS General Security Platform Software
							 Add:  fnameSU1ZAH10FE(16715807),				-- USG2200,SU1ZAH10FE,USG2210 AC Basic Configuration,(2GE,10FE,with 2*5FE MIC),with HS General Security Platform Software
							 Add:  fnameSU2Z42UAH(16715808),				  -- USG5100,SU2Z42UAH,USG5120BSR AC Host,with HS General Security Platform Software
							 Add:  fnameSU2Z43UHTO1(16715809),				  -- USG5100,SU2Z43UHT,USG5150BSR Host,with HS General Security Platform Software
							 Add:  fnameSU2Z43UHTO2(16715810),				  -- USG5500 1U Frame Unit
							 Add:  fnameSU2Z43UHT(16715811),				  -- USG5500 3U Frame Unit
				Add:  fnameSUAB13UAC(16715812),	            -- USG6600 SUAB13UAC  Frame Unit
				Add:  fnameNGFW1UL2(16715813),                    -- USG3600 L2 Frame Unit
				Add:  fnameNGFW1UL1(16715814),                    -- USG3600 L1 Frame Unit
				Add:  fnameNGFWSSM(16715815),                     -- NGFW SSM Frame Unit
							 Add:  bnameSU01MPUA(16719922),          -- SRG20,SU01MPUA,SRG20  Main Processing Unit ,2*1
							 Add:  bnameSU01MPUB(16719923),          -- SRG20,SU01MPUB,SRG20  Main Processing Unit ,2*1
							 Add:  bnameSU01MPUC(16719924),          -- SRG20,SU01MPUC,SRG20  Main Processing Unit ,2*1
							 Add:  bnameSU01ADPA(16719925),          -- SRG20,SU01ADPA,ADSL2+Multi-PVCs,2*2
							 Add:  bnameSU11SMX01(16719926),         -- Safety Product,SRG20,SU11SMX01,Enhanced Services Platform,ultra-low-end ,with CF Card, no Hard Disk
							 Add:  bnameSU11DMX02(16719927),         -- Safety Product,SRG20,SU11DMX02,Enhanced Services Platform,low-end , 2.5'' Hard Disk
							 Add:  bnameSU11DFX03(16719928),         -- Safety Product,SRG20,SU11DFX03, Enhanced Services Platform,mid-range , 2.5'' Hard Disk
							 Add:  bnameSU11DFX04(16719929),         -- Safety Product,SRG20,SU11DFX04, Enhanced Services Platform,mid-range , two 2.5'' Hard Disk
							 Add:  bnameSU11DFX05(16719930),         -- Safety Product,SRG20,SU11DFX05, Enhanced Services Platform,high-end ,with CF Card, two 2.5'' Hard Disk
							 Add:  bnameFWG2MPUA(16719931),          -- USG2200,FWG2MPUA,Main Process Unit Board,1*1
							 Add:  bnameSU11ADPA(16719932),          -- SRG20,SU11ADPA,ADSL2+Multi-PVCs,with HS General Security Platform Software,1*1
							 Add:  bnameFWF1E1FE(16719933),          -- USG2100,FWF1E1FE,1-Port Fast Ethernet Electrical Interface Board(RJ45),3*1
							 Add:  bnameSU11EPSEC(16719934),         -- USG5100,SU11EPSEC,High Speed IPsec Card,with HS General Security Platform Software
							 Add:  bnameSU51E4BY(16719935),          -- USG5100,SU51E4BY,4GE Electric Ports Bypass Card,with HS General Security Platform Software,1*1 duplicated with bnameSU51E4BY(16719960) add 'O'
							 Add:  bnameWCDMA(16719955),             --SVN5300,Security 3G board(WCDMA)
							 Add:  bnameTD-SCDMA(16719956),          --SVN5300,Security 3G board(TD-SCDMA)
							 Add:  bnameCDMA2000(16719957),          --SVN5300,Security 3G board(CDMA2000)
							 Add:  bnameSU51MPUB(16719958),          --USG5500,SU51MPUB,1U Main Processing Unit,1*1
							 Add:  bnameSU51SACC(16719959),          --USG5500,SU51SACC,Service Accelerate Card,1*1  duplicated with bnameSU51SACC(16719967) add 'O'
							 Add:  bnameSU51E4BY(16719960),          --USG5500,SU51E4BY,4GE Electric Ports Bypass Card,with HS General Security Platform Software,1*1
							 Add:  bnameSU51MPUA(16719961),          --USG5500,SU51MPUA,Main Processing Unit,1*1
							 Add:  bnameSU51X2G8(16719962),          --USG5500,SU51X2G8,2*10GE Optical Ports+8GE Electric Ports Interface Card,with HS General Security Platform Software,1*1
							 Add:  bnameSU51E2XSM(16719963),         --USG5500,SU51E2XSM,2*10GE Optical Ports Interface Card,with HS General Security Platform Software,3*1
							 Add:  bnameSU51E8GF(16719964),          --USG5500,SU51E8GF,8GE Optical Ports Interface Card,with HS General Security Platform Software,2*1
							 Add:  bnameSU51E8GE(16719965),          --USG5500,SU51E8GE,8GE Electric Ports Interface Card,with HS General Security Platform Software,1*1
							 Add:  bnameSU51E2XSF(16719966),         --USG5500,SU51E2XSF,2*10GE Optical Ports Interface Card,with HS General Security Platform Software,1*1
							 Add:  bnameSU51SACC(16719967),          --USG5500,SU51SACC,Service Accelerate Card,1*1
							 Add:  bnameSU51F2BY(16719968),          --USG5500,2 Link LC/UPC Optical Interface Bypass Protect Card
							 Add:  bnameSU51E8GFF(16719969),         --USG5500,8GE Optical Ports FIC Interface Card
							 Add:  bnameSU71DFX01(16719970),         --Safety Product,NIP5100,SU71DFX01,Enhanced Services Platform,High-end,for IPS
							 Add:  bnameSU51ESPA(16719971),          --NIP5100,ESP,SU51ESPA,X86 Process Card,1*1
							 Add:  bnameSU51ESPC(16719972),          --NIP5100,ESP,SU51ESPC,IPS Process Card,1*1
							 Add:  bnameSU51F2BY01(16719973),        --USG5500,SU51F2BY01,2 Link LC/UPC Multimode Optical Interface Bypass Protect Card,with HS General Security Platform Software
							 Add:  bnameSU51F2BY02(16719974),        --USG5500,SU51F2BY02,2 Link LC/UPC Singlemode Optical Interface Bypass Protect Card,with HS General Security Platform Software
							 Add:  bnameSUA1CPUA(16719975),          --Eudemon1000E-N CPU Card
							 Add:  bnameE8000ESU91SPUC(16748550),    --Eudemon8000E-X,SU91SPUC,X3 Service Processiong Unit(Base Board),with HS General Security Platform Software
							 Add:  bnameE8000ESU91SPUD(16748551),    --Eudemon8000E-X,SU91SPUD,X8&X16 Service Processiong Unit(Base Board),with HS General Security Platform Software
							 Add:  subbnameSVN5500CN1620(16740353),  -- SVN5500,SE41HSVA,High Speed SSL VPN Card,with HS General Security Platform Software,1*1
							 Add:  subbnameSUP34SFPCard(16732162),   --SUP,SUP34SFP,4-port GE Optical Interface Board(SFP),1*2
							 Add:  subbnameEudemon8000ESU91L4XX00(16748556),	   --SU91L4XX00 4 Port 10G Base WAN/LAN-XFP
							 Add:  subbnameEudemon8000ESU91L4XX01(16748557),	   --SU91L4XX01 4 Port 10G Base LAN/LAN-XFP
							 Add:  subbnameEudemon8000ESU91SPCB02(16748558),	   --Eudemon8000E-X,SU91SPCB02,20G Firewall Performance Expansion Card(oversea),with HS General Security Platform Software
							 Add:  subbnameEudemon8000ESU91SPCC01(16748559),	   --Eudemon8000E-X,SU91SPCC01,40G Firewall Processing Card,with HS General Security Platform Software
							 Add:  subbnameEudemon8000ESU91SPCB01(16748560),	   --Eudemon8000E-X,SU91SPCB01,80G Firewall Processing card,with HS General Security Platform Software

										"

		  --  Revision history R313C00
		  REVISION    "201302250000Z"
		  DESCRIPTION "V5.05,
							 Add:  frameMA5611S-DE16(561194),  -- Virtual frame MA5611S-DE16 of MA5611S FTTS device.
							 Add:  bnameHS26BVVS(155950),      -- 16 VDSL + Vectoring board of MA5611S FTTS device.
							 Add:  bnameH826BVVS(155951),      -- Master board of MA5611S FTTS device.
										"

		  REVISION    "201301310000Z"
		  DESCRIPTION "V5.03,
							 Modidy:  frameMa5662AH831MABC(561177),    -- Virtual Backplane of MA5662(SD5103) , master Frame:MA5662(SD5103).
										"

		  --  Revision history R13C00 add new mib
		  REVISION    "201301190000Z"
		  DESCRIPTION "V5.02,
							 Add:     bnameH801XESD(146137),        --  8 ports 10G EPON board of MA5600T.
										"

		  --  Revision history R312C00 add new mib
			REVISION    "201301140000Z"
		  DESCRIPTION "V5.01,
							 Add:     subbnameVPD(155949),      -- VECTOR Subboard VPD
							 "

		  --  Revision history R313C00 add new mib
		  REVISION    "201301040000Z"
		  DESCRIPTION "V5.00,
							 Add: fnameMA5611SH831Mabc(561191),  -- Virtual frame H831MABC of MA5652(sd5130) device.
							 Add: bnameH823UPVB(155947),         -- Master board of MA5652(sd5130) device.
							 Add: bnameHS23UPVB(155948),        -- 16 VDSL + Vectoring board of MA5652(sd5130) device.
							 "

		  REVISION    "201211260000Z"
		  DESCRIPTION "V4.99,
							 Add: bnameHS3BCVSB(155945),  -- 16 VDSL+16 POTS combo board of MA5622A.
							 Add: bnameHS3BCVSD(155946),  --  8 VDSL+ 8 POTS combo board of MA5622A.
							 "

		  --  Revision history
		  REVISION    "201211200000Z"
		  DESCRIPTION "V4.98,
							 Add:     bnameH801MCUD1(148005),        --  control board of MA5608T.
							 "

		  REVISION    "201211150000Z"
		  DESCRIPTION "V4.97,
							 Add: fnameMA5821H821Mabc(561189),  -- Virtual frame H821MABC of MA5821(sd5133) device.
							 Add: fnameMA5822H821Mabc(561190),  -- Virtual frame H821MABC of MA5822(sd5133) device.
							 Add: bnameH825XPUB(155944),        -- Master board of MA582x(sd5133)device.
							 "

		  --  Revision history
		  REVISION    "201211120000Z"
		  DESCRIPTION "V4.96,
							 Add: fnameMA5821H821Mabc(561189),  -- Virtual frame H821MABC of MA5821(sd5133) device.
							 Add: fnameMA5822H821Mabc(561190),  -- Virtual frame H821MABC of MA5822(sd5133) device.
							 Add: bnameH825XPUB(155942),        -- Master board of MA582x(sd5133)device.
							 "


		  --  Revision history
		  REVISION    "201210301500Z"
		  DESCRIPTION "V4.95,
							 Add:     bnameH801SPUF(146073),        -- interface board.
							 Add:     bnameH801MPWD(146074),        -- Power board of MA5608T.
							 "

			REVISION    "201209060000Z"
		  DESCRIPTION "V4.94,
							 Add:     bnameH801SCUK(148003),         --  MA5600T control board H801SCUK.
							 Add:     bnameH801SCUE(148004),         --  MA5600T control board H801SCUE.
							 "

		  REVISION    "201209030000Z"
		  DESCRIPTION "V4.93,
							 Modidy:  fnameMA5608H801Mabr(147525),    -- Backplane of the P300 broadband medium-capacity master Frame: H801MABR
							 "

			REVISION    "201208250000Z"
		  DESCRIPTION "V4.92,
							 Add:     bnameH802SCUN(148001),         --  MA5600T control board H802SCUN.
							 Add:     bnameH801SPUH(148002),         --  interface board of the MA5600T.
							 "

		  --  Revision history
			REVISION    "201208130000Z"
		  DESCRIPTION "V4.91,
							 Add:     fnameMA5623AR(147526),          --  MDU device MA5623A used as remote frame.
						  "

		  --  Revision history
			REVISION    "201208130000Z"
		  DESCRIPTION "V4.90,
							 Modidy:  fnameMA5694H821Mabc(561187),    -- Virtual frame H821MABC of MA5694(sd5130) device.
							 Modidy:  bnameH821CCIC(155935),          -- Master board of MA5694(sd5130)device.
							 Modidy:  bnameHS21GE4A(155936),          -- 4GE baoard for MA5694.
							 "

		  --  Revision history
			REVISION    "201207300000Z"
		  DESCRIPTION "V4.89,
							 Add:     bnameH831PAVD(155942),          -- 400W AC for MA5616.
							 Add:     bnameH831PAVDA(155943),         -- 400W AC+Vector for MA5616.
							 Add:     subbnameH833XP1A(155935),       -- 10 GPON Subboard
							 Add:     subbnameH833XP1C(155936),       -- 10 GPON Subboard
							 "

		  --  Revision history
			REVISION    "201207260000Z"
		  DESCRIPTION "V4.88,
							 Add:     bnameH832PDVAA(155933),   -- Double DC Power board H832PDVAA of  the  MA5616, supportting vector vp subboard.
							 Add:     subbnameVPB(155934),      -- VECTOR Subboard VPB
							 Update:  bnameVPB(155922)
							 Modidy:  bnameH831CCMC(155941),    -- Master board of MA5698(sd5130)device.
							 "

		 --  Revision history
		  REVISION    "201207250000Z"
		  DESCRIPTION "V4.87,
							 Add: fnameMA5698H821Mabc(561186),     -- Virtual frame H821MABC of MA5698(sd5130) device.
							 Add: fnameMA5691H821Mabc(561187),     -- Virtual frame H821MABC of MA5691(sd5130) device.
							 Add: fnameMA5678H821Mabc(561188),     -- Virtual frame H821MABC of MA5678(sd5130) device.
							 Add: bnameH831CCMC(155933),           -- Master board of MA5698(sd5130)device.
							 Add: bnameHS31GC4A(155934),           -- 4GE baoard(2GE+2GE COMBO) for MA5698.
							 Add: bnameH821CCIC(155935),           -- Master board of MA5691(sd5130)device.
							 Add: bnameHS21GE4A(155936),           -- 4GE baoard for MA5691.
							 Add: bnameH831CCLF(155937),           -- Master board of MA5678(sd5130)device.
							 Add: bnameH831E41B(155938),           -- 4E1 baoard for MA5678.
							 Add: bnameHS38ASRB(155939),           -- 32POTS baoard for MA5678.
							 Add: bnameHS31GE4A(155940),           -- 4GE baoard for MA5678.
						  "

		 --  Revision history
		 REVISION    "201207230000Z"
		 DESCRIPTION "V4.86, Modified the illegal comment symbol for FT."


		 --  Revision history
			REVISION    "201206130000Z"
		  DESCRIPTION "V4.85,
							 Add:     bnameH801MABR(147525),         --  Backplane of the P300 broadband master Frame: H801MABR.
							 Add:     subbnameH801CPCA(204923),      --  Clock subboard for the H801MCUD board.
							 Add:     subbnameH801CPCA(204933),      --  Clock subboard for the H801MCUD board.
							 Update:  bnameAF11SPLTA(745751),        --  AF11SPLTA.
							 Update:  bnameAF11SPPTA(745752),        --  AF11SPPTA.
						  "

		 --  Revision history
		  REVISION    "201206070000Z"
		  DESCRIPTION "V4.84,
							 Add: docsisPort(804),       -- docsis port of board HS33CDAA,the board has only one port(docsisPort).
						  "

		 --  Revision history
		  REVISION    "201205080000Z"
		  DESCRIPTION "V4.83,
							 Add: bnameH822CCKRA(155930),       -- Master board of MA5633(sd5130)device.
							 Add: bnameHS33CDAA(155931),        -- DOCSIS virtual board of MA5633
							 Add: bnameH83BVCL(155932),         -- 32 VDSL + Vectoring board of MA5616
							 Add: fnameMA5633H821Mabc(561185),  -- Virtual frame H821MABC of MA5633(sd5130) device.
						  "

		 --  Revision history
		  REVISION    "201203060000Z"
		  DESCRIPTION "V4.82,
							 Add:  bnameHS22CCVW(155928) ,    -- Master board of MA5623A(sd5130)device.
							 Add:  bnameHS3BVCMM(155929),        -- 48 VDSL baoard, supportting for vector
							 Add: fnameMA5623AH823Maba(561184),    -- Virtual frame H823MABA of MA5623A(sd5130) device.
						  "

		  --  Revision history
		  REVISION    "201202150000Z"
		  DESCRIPTION "V4.80,
						  Add: fnameMA562XS2H821Mabc(561182),    -- Virtual frame H821MABC of MA562X(sd5130) device.
						  Add: fnameMA562XS3H821Mabc(561183),    -- Virtual frame H821MABC of MA562X(sd5132) device.
						  Add: bnameH831CCUD(155923),        -- Master board of MA5616(SD5130) Box type device
						  Add: bnameH831PAIBA(155924),       -- Power board H831PAIBA of the MA561X
						  Add: bnameH825EPUB(155925),        -- Master board of MA5620/26(SD5132) Box type device
						  Add: bnameH823EPUB(155926),        -- Master board of MA5626-8 PoE(SD5130) Box type device
						  Add: bnameHS22EPFG(155927),        -- 8 GE board of MA5626(SD5130)
						  Add: subbnameH832TP1C(155668),          --1*10G EPON subboard
						"

		  --  Revision history
		  REVISION    "201202130000Z"
		  DESCRIPTION "V4.79,
						  Add 8 ports GPON board, 16 ports GPON board, 8 ports EPON board, 16 ports EPON board. The range of type is 146102 to 146136.
						"

		  --  Revision history
		  REVISION    "201202020000Z"
		  DESCRIPTION "V4.78,
						  Add: bnameH801SCUH(146101),         --two GE port and two 10GE port H801SCUH control board of MA5600T.
						"

		  --  Revision history
		  REVISION    "201201160000Z"
		  DESCRIPTION "V4.77,
						  Add: subbnameH821PRCA(155667),          --RFT-C subboard
						  "

		  --  Revision history
		  REVISION    "201201130000Z"
		  DESCRIPTION "V4.76,
						  Add: iODN devices to HWFrameType, HWPCBType, and HWSubPCBType, range 0x000B0000~0x000BFFFF, which are:
						  Add: fnameMPU3101B-AC-1U(720898),              --MPU3101B-AC-1U
						  Add: fnameMPU3101C-AC-1U(720899),              --MPU3101C-AC-1U
						  Add: fnameMPU3101D-AC-1U(720900),              --MPU3101D-AC-1U
						  Add: fnameMPU3101B-DC-1U(720901),              --MPU3101B-DC-1U
						  Add: fnameMPU3101C-DC-1U(720902),              --MPU3101C-DC-1U
						  Add: fnameMPU3101D-DC-1U(720903),              --MPU3101D-DC-1U
						  Add: fnameAF11FPUA(721153),                    --AF11FPUA
						  Add: fnameAF11FPUAT(721154),                   --AF11FPUAT
						  Add: fnameGPX147-iMODF-6U(721155),             --GPX147-iMODF-6U
						  Add: fnameAF11FATA(721156),                    --AF11FATA
						  Add: fnameAF11FATC(721409),                    --AF11FATC
						  Add: fnameAF11FATB(721410),                    --AF11FATB
						  Add: fnameGPX147-iODF3101(729089),             --GPX147-iODF3101
						  Add: fnameGXF147-iFDT3101(729090),             --GXF147-iFDT3101
						  Add: fnameGXF147-iFDT3101D(729091),            --GXF147-iFDT3101D
						  Add: fnameGXF147-FDT2107D(729092),             --GXF147-FDT2107D
						  Add: fnameGPX147-iFAT3101(729093),             --GPX147-iFAT3101
						  Add: fnameGPX147-iFAT3102-12(729094),          --GPX147-iFAT3102-12
						  Add: fnameGPX147-iFAT3102(729095),             --GPX147-iFAT3102
						  Add: fnameGPX147-ODF5101-CH2-1200mm(729096),   --GPX147-ODF5101-CH2-1200mm
						  Add: fnameGPX147-ODF5101-FH2-1200mm(729097),   --GPX147-ODF5101-FH2-1200mm
						  Add: fnameGPX147-ODF5101-CH2-900mm(729098),    --GPX147-ODF5101-CH2-900mm
						  Add: fnameGPX147-ODF5101-FH2-900mm(729099),    --GPX147-ODF5101-FH2-900mm
						  Add: fnameGPX147-ODF5101-CH9(729100),          --GPX147-ODF5101-CH9
						  Add: fnameGPX147-ODF5101-FH9(729101),          --GPX147-ODF5101-FH9
						  Add: fnameGXF147-iFDT3101D-A(729102),          --GXF147-iFDT3101D-A
						  Add: fnameGXF147-iFDT3103D-432(729104),        --GXF147-iFDT3103D-432
						  Add: fnameGPX147-iFAT3103T-16(729345),         --GPX147-iFAT3103T-16
						  Add: fnameGPX147-iFAT3103T-24(729346),         --GPX147-iFAT3103T-24
						  Add: fnameGPX147-iFAT3105T-32(729347),         --GPX147-iFAT3105T-32
						  Add: fnameGPX147-iFAT3105T-36(729348),         --GPX147-iFAT3105T-36
						  Add: fnameGPX147-iFAT3101TD-32(729349),        --GPX147-iFAT3101TD-32
						  Add: fnameGPX147-iFAT3101TD-36(729350),        --GPX147-iFAT3101TD-36
						  Add: fnameGPX147-iFAT3103TD-96-F(729351),      --GPX147-iFAT3103TD-96-F
						  Add: fnameGPX147-iFAT3103TD-96-P(729352),      --GPX147-iFAT3103TD-96-P
						  Add: fnameGPX147-SR5101-5U(737281),            --GPX147-SR5101-5U
						  Add: fnameGPX147-SR5101-5U-2(737282),          --GPX147-SR5101-5U-2
						  Add: fnameGPX147-SR5102-5U(737283),            --GPX147-SR5102-5U
						  Add: fnameGXF147-FAT5201T(737284),             --GXF147-FAT5201T

						  Add: bnameAF11TMSA(745473),                    -- AF11TMSA
						  Add: bnameAF11TMUA(745474),                    -- AF11TMUA
						  Add: bnameAF11TMLA(745475),                    -- AF11TMLA
						  Add: bnameAF11TMPA(745476),                    -- AF11TMPA
						  Add: bnameAF11STSA(745477),                    -- AF11STSA
						  Add: bnameAF11STUA(745478),                    -- AF11STUA
						  Add: bnameAF11STLA(745479),                    -- AF11STLA
						  Add: bnameAF11STPA(745480),                    -- AF11STPA
						  Add: bnameAF11SPSIA(745481),                   -- AF11SPSIA
						  Add: bnameAF11SPUIA(745482),                   -- AF11SPUIA
						  Add: bnameAF11SPLIA(745483),                   -- AF11SPLIA
						  Add: bnameAF11SPPIA(745484),                   -- AF11SPPIA
						  Add: bnameAF11SPSHA(745485),                   -- AF11SPSHA
						  Add: bnameAF11SPUHA(745486),                   -- AF11SPUHA
						  Add: bnameAF11SPLHA(745487),                   -- AF11SPLHA
						  Add: bnameAF11SPPHA(745488),                   -- AF11SPPHA
						  Add: bnameAF11SPSOA(745489),                   -- AF11SPSOA
						  Add: bnameAF11SPUOA(745490),                   -- AF11SPUOA
						  Add: bnameAF11SPLOA(745491),                   -- AF11SPLOA
						  Add: bnameAF11SPPOA(745492),                   -- AF11SPPOA
						  Add: bnameAF11SPSPA(745493),                   -- AF11SPSPA
						  Add: bnameAF11SPUPA(745494),                   -- AF11SPUPA
						  Add: bnameAF11SPLPA(745495),                   -- AF11SPLPA
						  Add: bnameAF11SPPPA(745496),                   -- AF11SPPPA
						  Add: bnameAF11SPSJA(745497),                   -- AF11SPSJA
						  Add: bnameAF11SPUJA(745498),                   -- AF11SPUJA
						  Add: bnameAF11SPLJA(745499),                   -- AF11SPLJA
						  Add: bnameAF11SPPJA(745500),                   -- AF11SPPJA
						  Add: bnameAF11SPSQA(745501),                   -- AF11SPSQA
						  Add: bnameAF11SPUQA(745502),                   -- AF11SPUQA
						  Add: bnameAF11SPLQA(745503),                   -- AF11SPLQA
						  Add: bnameAF11SPPQA(745504),                   -- AF11SPPQA
						  Add: bnameAF11SPSKA(745729),                   -- AF11SPSKA
						  Add: bnameAF11SPUKA(745730),                   -- AF11SPUKA
						  Add: bnameAF11SPLKA(745731),                   -- AF11SPLKA
						  Add: bnameAF11SPPKA(745732),                   -- AF11SPPKA
						  Add: bnameAF11SPSRA(745733),                   -- AF11SPSRA
						  Add: bnameAF11SPURA(745734),                   -- AF11SPURA
						  Add: bnameAF11SPLRA(745735),                   -- AF11SPLRA
						  Add: bnameAF11SPPRA(745736),                   -- AF11SPPRA
						  Add: bnameAF11SPSLA(745737),                   -- AF11SPSLA
						  Add: bnameAF11SPULA(745738),                   -- AF11SPULA
						  Add: bnameAF11SPLLA(745739),                   -- AF11SPLLA
						  Add: bnameAF11SPPLA(745740),                   -- AF11SPPLA
						  Add: bnameAF11SPSSA(745741),                   -- AF11SPSSA
						  Add: bnameAF11SPUSA(745742),                   -- AF11SPUSA
						  Add: bnameAF11SPLSA(745743),                   -- AF11SPLSA
						  Add: bnameAF11SPPSA(745744),                   -- AF11SPPSA
						  Add: bnameAF11SPSMA(745745),                   -- AF11SPSMA
						  Add: bnameAF11SPUMA(745746),                   -- AF11SPUMA
						  Add: bnameAF11SPLMA(745747),                   -- AF11SPLMA
						  Add: bnameAF11SPPMA(745748),                   -- AF11SPPMA
						  Add: bnameAF11SPSTA(745749),                   -- AF11SPSTA
						  Add: bnameAF11SPUTA(745750),                   -- AF11SPUTA
						  Add: bnameAF11SPLTA(745741),                   -- AF11SPLTA
						  Add: bnameAF11SPPTA(745742),                   -- AF11SPPTA
						  Add: bnameAF11STUB(745985),                    -- AF11STUB
						  Add: bnameAF11STSB(745986),                    -- AF11STSB
						  Add: bnameAF11STLB(745987),                    -- AF11STLB
						  Add: bnameAF11STPB(745988),                    -- AF11STPB
						  Add: bnameAF11STUC(745989),                    -- AF11STUC
						  Add: bnameAF11STSC(745990),                    -- AF11STSC
						  Add: bnameAF11STLC(745991),                    -- AF11STLC
						  Add: bnameAF11STPC(745992),                    -- AF11STPC
						  Add: bnameAF11TMUB(745993),                    -- AF11TMUB
						  Add: bnameAF11TMSB(745994),                    -- AF11TMSB
						  Add: bnameAF11TMLB(745995),                    -- AF11TMLB
						  Add: bnameAF11TMPB(745996),                    -- AF11TMPB
						  Add: bnameAF11TMUC(745997),                    -- AF11TMUC
						  Add: bnameAF11TMSC(745998),                    -- AF11TMSC
						  Add: bnameAF11TMLC(745999),                    -- AF11TMLC
						  Add: bnameAF11TMPC(746000),                    -- AF11TMPC

						  Add: subbnameAF11AMCX1(753921),                --AF11AMCX1
						  Add: subbnameAF11AMCB1(753922),                --AF11AMCB1
						  Add: subbnameAF11AMCC1(753923),                --AF11AMCC1
						  Add: subbnameAF11AMCD1(753924),                --AF11AMCD1
						  Add: subbnameAF11AMCX2(753925),                --AF11AMCX2
						  Add: subbnameAF11AMCB2(753926),                --AF11AMCB2
						  Add: subbnameAF11AMCC2(753927),                --AF11AMCC2
						  Add: subbnameAF11AMCD2(753928),                --AF11AMCD2
						  "
		  REVISION    "201111220000Z"
		  DESCRIPTION "V4.75,
						  Add: bnameH83BVCMM(155921),  -- 48 VDSL baoard, supportting for vectoring.
						  Add: bnameH831VPBB(155922),  -- vector control engine board.
						  "

		  --  Revision history
		  REVISION    "201112010000Z"
		  DESCRIPTION "V4.74,
						  Add: bnameH80BCVME(146099),   -- 48-channel VDSL2+ and POTS(combo) service board.
						  Add: bnameH801XGBC(146100),   -- 4-channel 10GE GPON board.
						"


		  --  Revision history
		  REVISION    "201111150000Z"
		  DESCRIPTION "V4.73,
						  Add: bnameH80XVPE(146097),   -- support vector board.
						  Add: bnameH80XVCM(146098),   -- support vector board.
						  "

		  --  Revision history
		  REVISION    "201111020000Z"
		  DESCRIPTION "V4.72,
						  Add: bnameH831CCUE(155912),        -- Master board of MA5616(SD5130) Box type device
						  "

		  --  Revision history
		  REVISION    "201110280000Z"
		  DESCRIPTION "V4.71,
						  Add: subbnameH821MODA(155666),          --56K MODEM subboard
						  "

		  --  Revision history
		  REVISION    "201110200000Z"
		  DESCRIPTION "V4.70,
						  Delete: bnameH806EPBD(146088),    -- 8EPON board.
						  Modify: bnameH803GPFD(146097) to bnameH803GPFD(146088).
						  "
		  --  Revision history
		  REVISION    "201110190000Z"
		  DESCRIPTION "V4.69,
						  Add: bnameH806EPBD(146088),   -- 8EPON board.
						  Add: bnameH807EPBD(146089),   -- 8EPON board.
						  Add: bnameH808EPBD(146090),   -- 8EPON board.
						  Add: bnameH806EPFD(146091),   -- 16EPON board.
						  Add: bnameH806GPBD(146092),    -- 8GPON board.
						  Add: bnameH807GPBD(146093),    -- 8GPON board.
						  Add: bnameH808GPBD(146094),    -- 8GPON board.
						  Add: bnameH801GPFD(146095),    -- 16GPON board.
						  Add: bnameH802GPFD(146096),    -- 16GPON board.
						  Add: bnameH803GPFD(146097),    -- 16GPON board.
						  "

		  --  Revision history
		  REVISION    "201109300000Z"
		  DESCRIPTION "V4.68,
						  Add: fnameMA5626POEH821Mabc(143451),  -- Virtual Frame of MA5626 POE Spec master Frame:H821MABC
						  Add: fnameMA5621AH831Mabc(561181),    -- Virtual Frame H831MABC of MA5621A device.
						  Add: bnameHS22EPFA(155910),         -- 24 POE board of 5626.
						  Add: bnameHS22EPFB(155911),         -- 16 POE board of 5626.
						  Add: bnameHS22EPFD(155913),         -- 8  POE board of 5626.
						  Add: bnameH832PDVA(155914),         -- Double DC Power board H832PDVA of  the  MA5616.
						  Add: bnameHS22EPFF(155915),        -- 4 FE board of MA5621A.
						  Add: bnameHS22COMF(155916),        -- 2-channel Serial board of MA5621A.
						  Add: bnameH823CCIQ(155917),        -- Master board of MA5621A Box type device.
						  Add: bnameH83BCVL(155918),         -- 32 VDSL+32 POTS combo board of MA5616.
						  Add: bnameHS22CCVB(155920),        -- Master board of MA5622A(SD5103) Box type device.
						  Add: subbnameH831XP1A(155665),     --10G GPON subboard.
						  Modify: bnameH822EPUC to bnameHS22CCVA.
						  Modify: bnameH828ASNB to bnameHS3BCVSE.
						  Modify: bnameHS25VDUE to bnameHS3BVDSE.
						  "

	 --  Revision history
		  REVISION    "201109260000Z"
		  DESCRIPTION "V4.67,
						  Add: fnameMA5632DH821Mabc(561179),   -- Virtual frame H821MABC of 5632 device with GE and Auto.
						  Add: fnameMA5616H831Mabb(561180),   -- vector frame of 5616 ARM device.
						  Modify: fnameMA5632H821Mabc to fnameMA5632SH821Mabc.
						  "

		  --  Revision history
		  REVISION    "201109230000Z"
		  DESCRIPTION "V4.66,
						  Add: fnameMA5603H802Mabo(147523),     -- Backplane of the P300 broadband medium-capacity master Frame: H802MABO
						  "

		  --  Revision history
		  REVISION    "201109160000Z"
		  DESCRIPTION "V4.65,
						  Add: bnameH808EPSD(146087),   -- 8EPON board.
						  "

		  --  Revision history
		  REVISION    "201109050000Z"
		  DESCRIPTION "V4.64,
						  Add: fnameMA5669H831Mabc(561178),   -- Virtual Frame H831MABC of MA5669 device.
						  Add: bnameH822EPUD(155827),         -- 1-port autoAdpt Master board of MA5669 Box type device.
						  Add: bnameH822UPIG(155828),         -- 2-port GE board without POE of MA5669.
						  Add: bnameH822UPWG(155829),         -- 2-port GE board with POE of MA5669.
						  Add: frameMa5662AH831MABC(561175),  -- Virtual Backplane of MA5662(SD5103) , master Frame:MA5662(SD5103).
						  Add: bnameH82BCVMM(155825),         -- Master board of MA5662(SD5103) Box type device.
						  Add: bnameHS3BVDMM(155826),         -- 48-channel VDSL2  board for MA5662(SD5103).
						  Modify: fnameMA5653H831Mabc to fnameMA5661H831Mabc.
						  Modify: bnameH832PAIA to bnameH831PAIC.
						  "

		  --  Revision history
		  REVISION    "201108250000Z"
		  DESCRIPTION "V4.63,
						  Add: frameH612MainHABA(196615),      -- Rear-access PVM high-density master Frame, with the H612HABA backplane.
						  Add: frameH612SlaveHABA(196616),     -- Rear-access PVM high-density slave Frame, with the H612HABA backplane.
						  Add: bnameH612HWCB(262216),          -- H612HWCB board.
						  Add: bnameH612HWTB(262217),          -- H612HWTB board.
						  Add: bnameH612PVMD(262218),          -- H612PVMD main board.
						  "

		  --  Revision history
		  REVISION    "201108080000Z"
		  DESCRIPTION "V4.62,
						  Add: frameH612SlaveHABD(196611),     -- Front-access PVM high-density slave Frame, with the H612HABD backplane.
						  Add: frameH612MainHABT(196612),      -- Front-access PVM high-density master Frame, with the H612HABD backplane.
						  Add: frameH612SlaveHABT(196613),     -- Front-access PVM high-density slave Frame, with the H612HABD backplane.
						  Add: frameH612SlaveHABT1(196614),    -- Front-access PVM high-density slave Frame, with the H612HABE backplane.
						  Add: bnameH612PVMT(262214),          -- H612PVMT board.
						  Add: bnameGIU(262215),               -- GIU board(H612IPMD).
						  "

		  --  Revision history
		  REVISION    "201107040000Z"
		  DESCRIPTION "V4.61,
						  Add: fnameMA5631SH821Mabc(561176),  -- Virtual Backplane of MA5631(2 IN 2 OUT) Spec master Frame:H821MABC.
						  "

		  --  Revision history
		  REVISION    "201107010000Z"
		  DESCRIPTION "V4.60,
						  Add: fnameMA5632H821Mabc(561173),   -- Virtual frame H821MABC of 5632 device.
						  Add: fnameMA5653H831Mabc(561174),   -- Virtual Frame H821MABC of 5653 device.
						  Add: fnameMA5612AH831MABL(561175),  -- Frame H831MABL of 5612A device.
						  Add: bnameH822CCJS(155817),         -- Master board of MA5632 Box type device.
						  Add: bnameH832PAIA(155818),         -- Power board H832PAIA of the MA5616.
						  Add: bnameH83BVDLE(155819),         -- 32-port VDSL interface board.
						  Add: bnameH836ADPE(155820),         -- 64-port ADSL2 interface board.
						  Add: bnameH82BCVRJ(155821),         -- Master board of MA5653 Box type device.
						  Add: bnameHS2CCVPE(155822),         -- 64 VDSL+64 POTS combo board of MA5653.
						  Add: bnameH821PTBA(155823),         -- Power board H821PTBA of the MA5653
						  Add: bnameHS21WF1A(155824),         -- WIFI board HS21WF1A of the MA5653.
						  "

		  --  Revision history
		  REVISION    "201106130000Z"
		  DESCRIPTION "V4.59,
						  Change: eponOltPor to eponOltPort,
						  "

		  --  Revision history
		  REVISION    "201106070000Z"
		  DESCRIPTION "V4.58, Add a new menu vdslPstnPort(701) of HWPortType
						  "
		  REVISION    "201105030000Z"
		  DESCRIPTION "V4.57,
						  Add: bnameH85BCVME(146070),    --48-channel VDSL2+ and POTS(combo) service board
						  Add: bnameH801VRGA(146071),    --Virtual Route Gateway Board
						  Add: bnameH806EPBD(146072),    --8EPON board
						  "

		  REVISION    "201103010000Z"
		  DESCRIPTION "V4.56,
						  Add: bnameH805EPBD(146086),    --8EPON board
						  "

		  --  Revision history
		  REVISION    "201102220000Z"
		  DESCRIPTION "V4.55, The following boards are modified, and the fname of fnameMA5628OSH821Mabc(561172) is added.
						  bnameHS22GRVD(155810),  -- 8  VDSL2 + over POTS + RF board.
						  fnameMA5628OSH821Mabc(561172),    -- Backplane of MA5628O Spec master Frame:H821MABC
						  "
		  --  Revision history
		  REVISION    "201101270000Z"
		  DESCRIPTION "V4.54, The following boards are modified.
						  serialSrvPort(799),              -- serial service port
						  fnameMA5626H821Mabc(143368),  -- Virtual Backplane of MA5626(Reduce Cost) Spec master Frame:H821MABC
						  "
		  --  Revision history
		  REVISION    "201101260000Z"
		  DESCRIPTION "V4.53,
						  Change: bnameH80BVDPM to bnameH80XVDP,
						  Change: bnameH801ASPB to bnameH80XASP,
						  Delete: bnameH80BVDPE,
						  Add: bnameH805GPBD(146085),    -- 8GPON board
						  "

		  --  Revision history
		  REVISION    "201101140000Z"
		  DESCRIPTION "V4.52, The following boards are modified.
						  bnameH831CCUC(155703),        -- Master board of MA5616(SD5103) Box type device
						  bnameH831CCUN(155716),        -- Master board of MA5631(SD5103) Box type device
						  "

			--  Revision history

		  REVISION    "201101110000Z"
		  DESCRIPTION "V4.51, The board of bnameH822CCGJA(155718) is added and changed."

		  --  Revision history
		  REVISION    "201012280000Z"
		  DESCRIPTION "V4.50, The following boards are added.
						  bnameH803TPBA(146083),        -- 2-port 10G EPON interface board
						  bnameH803TPBC(146084),        -- 4-port 10G EPON interface board
						  "

		  --  Revision history
		  REVISION    "201012130000Z"
		  DESCRIPTION "V4.49, The board of bnameH822CCGJA(155713) is added."

		  REVISION    "201011260000Z"
		  DESCRIPTION "V4.48, The following boards and subboard are added for MA5652 & MA5622 & MA5621 & MA5612 & MA5616 device:
						  fnameMA5622SH831Mabc(561169),  -- Backplane of MA5622 Spec master Frame:H831MABC.
						  fnameMA5652SH831Mabc(561170),  -- Backplane of MA5652 Spec master Frame:H831MABC.
						  fnameMA5621H831Mabc(561171),   -- Backplane of MA5621 Spec master Frame:H831MABC.
						  bnameH832PDIA(155803),  -- 2 DC input power board of MA5616
						  bnameH822EPUC(155804),  -- Master board of MA5622 Box type device.
						  bnameH828ASNB(155805),  -- 16-channel POTS board of MA5622.
						  bnameHS25VDUE(155806),  -- 16-channel vdsl2 board of MA5622.
						  bnameH832EPUA(155807),  -- Master board of MA5652 Box type device.
						  bnameHS22VDRE(155808),  -- 24 VDSL2 + over POTS board.
						  bnameHS22VDGE(155809),  -- 16 VDSL2 + over POTS board.
						  bnameHS22VDJE(155810),  -- 8  VDSL2 + over POTS board.
						  bnameHS22VDOE(155811),  -- 24 VDSL2 + over ISDN board.
						  bnameHS22VDHE(155812),  -- 16 VDSL2 + over ISDN board.
						  bnameHS22VDKE(155813),  -- 8  VDSL2 + over ISDN board.
						  bnameH822CCIQ(155814),  -- Master board of MA5621 Box type device.
						  bnameH821EPFF(155815),  -- 4-channel GE board of MA5621.
						  bnameH821COME(155816),  -- 4-channel Serial board of MA5621.
						  subbnameH832TP2C(155663),  --10G EPON subboard.
						  subbnameH832TP2D(155664),  --10G EPON subboard.
						  "

		  REVISION    "201011150000Z"
		  DESCRIPTION "V4.47, The following boards are added.
						  bnameH80BCAME(146069),        -- 48-channel ADSL2+ and POTS(combo) service board
						  bnameH80BVDPM(146066),        -- 64-channel VDSL2 over POTS service board
						  bnameH80BVDPE(146067),        -- 64-channel VDSL2 service board
						  bnameH801PAIC(146082),        -- H801PAIC Power board.
						  Modified the description of hwTrapType."

		  REVISION    "201009290000Z"
		  DESCRIPTION "V4.46, The following boards are added:
						  Add 48L VDSL board of MA5616:bnameH83BVDMM(155802)
						  "

		  REVISION    "201009250000Z"
		  DESCRIPTION "V4.45, The following boards are added:
						  Add 24L VDSL board of MA5616:bnameH83BVDSB(155800)
						  Add 24L POTS board of MA5612:bnameH837ASMB(155801)
						  "

		  REVISION    "201009010000Z"
		  DESCRIPTION "V4.44, modified the description of the objects in this MIB file for standard trap."

		  REVISION    "201008110000Z"
		  DESCRIPTION "V4.43, The following value are added for the MxU MA5631 device:
						  fnameMA5631SH821Mabc(561168), -- Virtual Backplane of MA5631(SD5103) Spec master Frame:H821MABC
						  bnameH832CCUC(155716),        -- Master board of MA5631(SD5103) Box type device
						  bnameH831HE1A(155717),        -- 1 port EoC board of MA5631(SD5103)
						  subbnameH831UP2D(155661),   -- Auto adapt upstream subboard, which is used for the MA5631(SD5103) upstream service
						  eocport(803),                 -- EoC master RF port
						  "

		  REVISION    "201007300000Z"
		  DESCRIPTION "V4.42, The following SubBoard is added for the MxU MA5616 device:
						  subbnameH836ASDM(155662),          --VOIP 128 Tunnel DSP Subboard H836ASDM
						  "

		  REVISION    "201007150000Z"
		  DESCRIPTION "V4.41, The following shelves, boards are added and changed.
						  Add 24L VDSL2(IFX,17a),GPON(RF) ,Over POTS service board of MA5652:bnameH821GRVAA(155713)
						  Change 24L VDSL2(IFX,17a),GPON(RF) ,Over POTS service board of MA5652:bnameH821GRVAB(155715)"

		  REVISION    "201007080000Z"
		  DESCRIPTION "V4.40, The following Backplane is added for the SCU 300mm Frame:
						  fnameMA5600H801Mabv(143359),     -- Backplane(19 Inch) of the P300 new broadband master Frame: H801MABV"

		  REVISION    "201006170000Z"
		  DESCRIPTION "V4.39, Modify the Chinese characters in Mib files."

		  REVISION    "201006010000Z"
		  DESCRIPTION "V4.38, The following shelves, boards are added.
						  Add 24L VDSL2(IFX,17a),GPON(RF) ,Over POTS service board of MA5652:bnameH821GRVA(155713)
						  Add 64-channel VoIP POTS service board of MA5616: bnameASP(155714)"

		  REVISION    "201005150000Z"
		  DESCRIPTION "V4.37, Add Virtual Backplane of MA5628(SD5103) Spec master Frame: fnameMA5628SH821Mabc,
						  Add Master board of MA5628(SD5103) Box type device: bnameH822CCGJ,
						  Add 4E1 Vitual board of H822CCGJ: bnameH831EDVB."

		  REVISION    "201004280000Z"
		  DESCRIPTION "V4.36, The following shelves, boards are added.
						  fnameSRGFWG2BKPA(190001),       -- SRG master Frame: FWG2BKPA(R2 1U)
						  fnameSRGSU11BKPA(190002),       -- SRG master Frame: SU11BKPA(R2 2U)
						  fnameSRGSU21BKPA(190003),       -- SRG master Frame: SU21BKPA(R2 3U)
						  bnameSU11EWFS(190012),          -- 32-pots fxs board
						  bnameSU11E4MS(190013),          -- 4-pots fxs board
						  bnameSU11E4MO(190014),          -- 4-pots fxo board
						  bnameSU11E4MM(190015),          -- 2-pots fxs + 2-pots fxo board
						  bnameSU11E2MV(190016),          -- 2-pots ve1 board
						  bnameSU11UP2A(190017),          -- PON board(3 mode)"

		  REVISION    "201004230000Z"
		  DESCRIPTION "V4.35, The following shelves, boards, subboard are added.
						  fnameWLANWS6603(160000): Backplane of the WLAN V1R2 master Frame: WS6603.
						  fnameWLANWAC(160001): Backplane of the WLAN V1R3 master Frame: WAC.
						  bnameWA611WACA(160000): Master board of WS6603(WLAN V1R2) Box type device.
						  bnameWA611PAIA(160001): power board of WS6603(WLAN V1R2) Box type device.
						  bnameWA611PDIA(160002): power board of WS6603(WLAN V1R2) Box type device.
						  bnameH801WACA(160003): AC service Board of WS6800/WS6803(WLAN V1R3).
						  subbnameWA611POEA(160000): Power Subboard of WA611WACA."

		  REVISION    "201004090000Z"
		  DESCRIPTION "V4.34, The board of bnameH802P2CA(146065) is added."

		  REVISION    "201003260000Z"
		  DESCRIPTION "V4.33, Modified the revision."

		  REVISION    "201003230000Z"
		  DESCRIPTION "V4.32, DT requirements are implemented and the syntax and semantics of SIMPLETEST are changed."

		  REVISION    "201003090000Z"
		  DESCRIPTION "V4.31, The following boards are added.
						  bnameE8000ESUP3SPUA02IPS(16748548):IPS Service Processing Unit,
						  with HS General Security Platform S
						  bnameE8000EKW51ESPUIPS(16748549): IPS SPU Board ,Service Processing Unit
						  subbnameUSG9100E2XS(16748570): 2*SFP+ Interface Broad,
						  with HS General Security Platform Software
						  subbnameUSG9100E16GF(16748571): 16*SFP Interface Board,
						  with HS General Security Platform Software."

		  REVISION    "201003020000Z"
		  DESCRIPTION "V4.30, The board of bnameH821EPFE(155709) is added."

		  REVISION    "201002220000Z"
		  DESCRIPTION "V4.29, The enumerated value of H802EDTB is added."

		  REVISION    "201002110000Z"
		  DESCRIPTION "V4.28, The NMS enumerated value of H85BVDMD is added and revision description is added."

		  REVISION    "201001290000Z"
		  DESCRIPTION "V4.27, 1 The syntax of SIMPLETEST MIB BROWSER is changed.
							2 The MIB description is changed."

		  REVISION    "201001260000Z"
		  DESCRIPTION "V4.26, One board is added for the SVN5300.
						  bnameSE21MPUA(16719954): SVN5300,Security virtual Gateway Mainboard(4GE). "

		  REVISION    "201001120000Z"
		  DESCRIPTION "V4.25, Two types for daughter board subbnameH801CKMA are recorded in MIB files.
						  One enumerated value is 145935 and another enumerated value is 146020.
						  The two values, however, refers to the same daughter board, and enumerated
						  value 145935 is used in codes. Therefore, enumeration definition of value 146020 is deleted."

		  REVISION    "200912170000Z"
		  DESCRIPTION "V4.24,The following shelves are added.
						  fnameSRGZ23UHT(16715796):SRG3260,SRGZ23UHT,SRG3260 Host,
						  with HS General Security Platform Software.
						  fnameSU2Z12UAH(16715797):USG5100,SU2Z12UAH,USG5120 AC Host,
						  with HS General Security Platform Software.
						  fnameSU2Z12UDH(16715798): USG5100,SU2Z12UDH,USG5120 DC Host,
						  with HS General Security Platform Software.
						  fnameSU2Z13UHT(16715799):USG5100,SU2Z13UHT,USG5150 Host,
						  with HS General Security Platform Software.
						  fnameSU2Z22UAH(16715800):USG5100,SU2Z22UAH,USG5120BSR AC Host,
						  with HS General Security Platform Software.
						  fnameSU2Z22UDH(16715801): USG5100,SU2Z22UDH,USG5120BSR DC Host,
						  with HS General Security Platform Software.
						  fnameSU2Z23UHT(16715802): USG5100,SU2Z23UHT,USG5150BSR Host,
						  with HS General Security Platform Software.
						  fnameSRGZ12UAH(16715803):SRG3230,SRGZ12UAH,SRG3230 AC Host,
						  with HS General Security Platform Software.
						  fnameSRGZ22UAH(16715804):SRG3240,SRGZ22UAH,SRG3240 AC Host,
						  with HS General Security Platform Software.
						  fnameSRGZ22UDH(16715805): SRG3240,SRGZ22UDH,SRG3240 DC Host,
						  with HS General Security Platform Software.
						  fnameSRGZ13UHT(16715806): SRG3250,SRGZ13UHT,SRG3250 Host,
						  with HS General Security Platform Software."

		  REVISION    "200912080000Z"
		  DESCRIPTION "V4.23, Daughter board H801M2XA(146025) is added."

		  REVISION    "200912040000Z"
		  DESCRIPTION "V4.22,The following boards are added.
						  bnameSRGM1WCDMA(16719917): SRG,SRGM1WCDMA,USB 3G WCDMA Card.
						  bnameSRGM1CD2K(16719918): SRG,SRGM1CD2K,USB 3G CDMA2000.
						  bnameSRGM1TD(16719919): SRG,SRGM1TD,USB 3G TDSCDMA.
						  bnameSU11X86HS02(16719920): Safety Product,USG2200,SU11X86HS02,
						  Enhanced Services Platform Enterprise Version,X86 Board,CPU T7500,
						  2GB Memory,160G Enterprise Hard Disk.
						  bnameSU11X86HS01(16719921): Safety Product,USG2200,SU11X86HS01,
						  Enhanced Services Platform Common Version,X86 Board,CPU T7500,
						  2GB Memory,160G Universal Hard Disk."

		  REVISION    "200911250000Z"
		  DESCRIPTION "V4.21,The following boards are added for the USG2200 V3R2.
						  bnameSU11F8E1(16719905): SRG20,SU11F8E1,8-port E1 Interface Card-DB44-75ohm.
						  bnameSU11FC8E1(16719906): SRG20,SU11FC8E1,8-port Channelized E1 Interface Card-DB44-75ohm.
						  bnameSU11F4E1(16719907): SRG20,SU11F4E1,4-port E1 Interface Card-DB44-75ohm.
						  bnameSU11FC4E1(16719908): SRG20,SU11FC4E1,4-port Channelized E1 Interface Card-DB44-75ohm.
						  bnameSU11APWN(16719909): SRG20,SU11APWN,WLAN Service Board.
						  bnameSU21MPUA(16719910): USG5100,SU21MPUA,Main Process Unit Board .
						  bnameSU11MPUA(16719911): USG5100,SU11MPUA,Main Process Unit Board .
						  bnameFWE1E4GE(16719912): USG5100,FWE1E4GE,4-port Gigabit Ethernet Interface Card(RJ45).
						  bnameFWG1F2F2C(16719913): USG2200,FWG1F2F2C,2FE(RJ45)+2FE(RJ45&SFP) MIXED INTERFACE CARD.
						  bnameSU21F18S2(16719914): USG5100,SU21F18S2,18FE(RJ45)+2GE(SFP) Mixed Interface Card.
						  bnameSU21G16S4(16719915): USG5100,SU21G16S4,16GE(RJ45)+4GE(SFP) Mixed Interface Card.
						  bnameSU11E8F2G(16719916): SRG20,SU11E8F2G,8FE(RJ45)+2GE(RJ45) Mixed Interface Card."

		  REVISION    "200911190000Z"
		  DESCRIPTION "V4.20, The boards of the following two types are added for the USG2100.
						  bnameFWF1MPUCO1(16719903),bnameSU11ADPAO2(16719904),
						  The boards of the following four types are added for the USG3000.
						  bnameRTB21CT1(16719950),bnameRRTB21CE1(16719951),bnameRTB21T1(16719952),
						  bnameRTB21E1(16719953).
						  The daughter board of the following type is added for the TUSG9100.
						  subbnameUSG9100SU61X2G16(16748569).
						  The following port is added for the USG3000.T1(16711685)."

		  REVISION    "200911170000Z"
		  DESCRIPTION "V4.19, Many MIB compilation problems are found in DT tests.
						  These compilation problems are solved and MIBs are archived."

		  REVISION    "200911110000Z"
		  DESCRIPTION "V4.18, MIB enumerated values are added for the 562x, the 5612,
						  and the 5616 that are in SD5103 architecture.
						  The following boards are added.
						  bnameH822EPUB(155702): Master board of MA562X(SD5103) Box type device.
						  bnameH832CCUB(155703): Master board of MA5616(SD5103) Box type device.
						  bnameH832CCFE(155704): Master board of MA5612(SD5103) Box type device.
						  bnameH835CALE(155705): 32 ADSL+32 POTS combo board .
						  bnameH831EIUD(155706): 4GE(combo)+4FE board.
						  bnameH831E81A(155707): 8E1 board.
						  bnameH831EPWA(155708): POE board.
						  The following shelves are added.
						  fnameMA562XSH821Mabc(561164): Virtual Backplane of MA562X(SD5103) Spec master Frame H821MABC.
						  fnameMA5616SH831MABA(561165): Backplane of the MA5616(SD5103) master Frame  H831MABA.
						  fnameMA5612SH831MABL(561166): Backplane of the MA5612(SD5103) master Frame  H831MABL.
						  The following daughter boards are added:
						  subbnameH831UP2A(155658)L: Auto adapt upstream subboard, which is used for the MDU upstream service.
						  subbnameH831UP2C(155659): Auto adapt upstream subboard with Clock, which is used for the MDU upstream service.
						  subbnameH831GR1A(155660): RF upstream subboard, which is used for the MDU upstream service.
						  The following ports are added.
						  autoAdptPort(800): auto adpt port.
						  catvPort(801): CATV port.
						  In addition, MIB compilation of version 4.17 fails; 3G in version 4.18 is changed to _3G."

		  REVISION    "200910300000Z"
		  DESCRIPTION "V4.17, VEPort(16711681): The Virtual Ethernet (VE) is applied to the PPPoEoA and IPoEoA.
						  It functions on the interface board. Externally it features Ethernet attributes.
						  3GPort(16711682):3G supports three wireless communication mode,
						  including both WCDMA/CDMA2000/TD-SCDMA and corresponding 2G mode.
						  SerialPort(16711683): The serial port is used for the exchange of information between computers
						  or devices one bit at a time over a single channel. Serial communications can be synchronous
						  or asynchronous. Both sender and receiver must use the same baud rate, parity, and control information.
						  DialerPort(16711684):The dialer interface is used as dialing interface of pppoe client, supports pppoe protocol."

		  REVISION    "200910290000Z"
		  DESCRIPTION "V4.16, The NMS enumerated value of H802OPGD needs to be added for the MA5600V8R8."

		  REVISION    "200910280000Z"
		  DESCRIPTION "V4.15, The NMS enumerated value of H801CKMC and the enumerated value of H808ASPB.
						  are added for V8R7.
						  bnameH808ASPB(146081): H808ASPB BOARD 64-channel voice service board of the MA5600.
						  subbnameH801CKMC(146024):Clock subboard for the H801SCUL and H801SCUN board."

		  REVISION    "200910270000Z"
		  DESCRIPTION "V4.14, The following shelf, control board, ADSL board and power board are added for the ATN931.
						  fnameATN931TNC1AFB(561163): Backplane of the ATN931 master Frame: TNC1AFB.
						  bnameH831CCEL(155699): Master board of ATN931 Box type device.
						  bnameH835BVJA(155700): adsl board of ATN931 Box type device.
						  bnameTNC1PIU(155701): power board of ATN931 Box type device."

		  REVISION    "200910160000Z"
		  DESCRIPTION "V4.13,The following boards are added for the USG2100.
						  bnameFWF1SPUA(16719900):FWF1SPUA,Main Process Unit Board,USG2100.
						  bnameFWF1SPUB(16719901):FWF1SPUB,Main Process Unit Board,USG2100.
						  bnameFWF1MPUD(16719902):FWF1MPUD,Main Process Unit Board,USG2100."

		  REVISION    "200910130000Z"
		  DESCRIPTION "V4.12,  USG2200,USG2100
						  wifi(233):WIFI card communicates with WIFI terminals as a wireless AP,
						  and supports IEEE 802.11b/ 802.11g."

		  REVISION    "200910120000Z"
		  DESCRIPTION "V4.11, 1.Mother board H831CCIK is added because the MXU ATN930 is independent of the OT920.
						  The NMS enumerated value corresponding to the mother board needs to be applied for.
						  Apply for the NMS enumerated value:
						  bnameH831CCIK(155698):Master board of ATN930 Box type device.
						  2. The 5620 supports 8 FE + 8 POTS mother board. The name of the virtual 8 POTS board
						  is changed from H822ASL to H848ASLB according to naming rules.
						  The NMS enumerated value (155697) that is applied for is not changed.
						  bnameH848ASLB(155697): MA562XP 8POTS."

		  REVISION    "200306280000Z"
		  DESCRIPTION "V1.00, Complete the Draft."
				::= { huawei 20021210 }

		  HWErrorCode ::= TEXTUAL-CONVENTION
				STATUS deprecated
				DESCRIPTION
					 "This object is not used any longer.SNMP expand Error code defintion."
				SYNTAX Integer32

		  HWFrameType ::= TEXTUAL-CONVENTION
				STATUS current
				DESCRIPTION
					 "This data type is used as the syntax of the
					 hwframeType object in the definition of
					 HUAWEI-DEVICE-MIBs hwframeTable.

					 The definition of this textual convention with the
					 addition of newly assigned values is published
					 periodically by the Huawei MIB Criterion Group, every
					 value indicate a frame produced by Huawei.
						"
				SYNTAX INTEGER
					 {
					 fnameUnknow(1),
-- MD5500:
					 fnameMd16(2),                   -- MD 16 Slot Frame
					 fnameMd8(3),                    -- MD 8  Slot Frame
					 fnameMd4(4),                    -- MD 4  Slot Frame
					 fnameMa16(5),                   -- MA 16 Slot Frame
					 fnameMa8(6),                    -- MA 8  Slot Frame
					 fnameMa4(7),                    -- MA 4  Slot Frame
					 fnameSmx16(8),                  -- MA 16 Slot Slave Frame
					 fnameRsa(9),                    -- RSA Frame
					 fnameRsp19(10),                 -- RSP 19 Slot Frame
					 fnameRsp15(11),                 -- RSP 15 Slot Frame
					 fnameRsp14(12),                 -- RSP 14 Slot Frame
					 fnameRsp12(13),                 -- RSP 12 Slot Frame
					 fnameRsp10(14),                 -- RSP 10 Slot Frame
					 fnameRsp6A(15),                 -- RSP 6  Slot A Type Frame
					 fnameRsp6B(16),                 -- RSP 6  Slot B Type Frame
					 fnamePv819(17),                 -- PV8 19 Slot Frame
					 fnamePv815(18),                 -- PV8 15 Slot Frame
					 fnamePv814(19),                 -- PV8 14 Slot Frame
					 fnamePv812(20),                 -- PV8 12 Slot Frame
					 fnamePv810(21),                 -- PV8 10 Slot Frame
					 fnamePv86A(22),                 -- PV8 6 Slot A Type Frame
					 fnamePv86B(23),                 --PV8 6 Slot B Type Frame
-- New UA3000 Frame
					 fnameHubm(24),                  -- Rear-access master Frame of the HONET
					 fnameHube(25),                  -- Front-access master Frame of the HONET
					 fnameHubf(26),                  -- Front-access slave Frame of the HONET
-- New MD5500 Frame that supports the UA management
					 fnameUamr(27),                  -- UA R Frame, with an HUBM backplane
					 fnameUasr(28),                  -- UA R Frame, with an HUBS backplane
					 fnameUafmr(29),                 -- UA R Frame, with an HUBE backplane
					 fnameUafsr(30),                 -- UA R Frame, with an HUBF backplane
					 fnameUamv(31),                  -- UA V Frame, with an HUBM backplane
					 fnameUasv(32),                  -- UA V Frame, with an HUBS backplane
					 fnameUafmv(33),                 -- UA V Frame, with an HUBE backplane
					 fnameUafsv(34),                 -- UA V Frame, with an HUBF backplane
					 fnameUabmr(35),                 -- UA R Frame, with an HUBB backplane
					 fnameOnu60ar(36),               -- UA R Frame, with an HUBO backplane
					 fnameOnuf01D100r(37),           -- UA R Frame, with an HUBL backplane
					 fnameUabmv(38),                 -- UA V Frame, with an HUBB backplane
					 fnameOnu60av(39),               -- UA V Frame, with an HUBO backplane
					 fnameOnuf01D100v(40),           -- UA V Frame, with an HUBL backplane
					 fnameHubs(41),                  -- UA broadband service Frame, with an HUBS backplane
					 fnameHubb(42),                  -- UA broadband service Frame, with an HUBB backplane
					 fnameHubl(43),                  -- UA broadband service Frame, with an HUBL backplane
					 fnameMa7(44),                   -- MA5103 master Frame that provides seven slots
					 fnameSmxMa4(45),                -- MA5103 slave Frame that provides four slots
					 fnameSmxMa7(46),                -- MA5103 slave Frame that provides seven slots
					 fnameMdb16(47),                 -- Large-capacity backplane of the MD5500
-- Uniformed Frame of the Musa:
					 fnameMusa(50),
-- MA5200:
					 fnameMusa5200E(51),             -- The MA5200E is a box-shaped device of 1 U height.
					 fnameMusa5200F(52),             -- The MA5200F is a box-shaped device of 2 U height.
-- AG:
					 fnamePvm10(60),
					 fnamePvm6B(61),
					 fnamePvm6A(62),                 -- AG's 160A master Frame, with an HMB backplane
					 fnamePvmUam(63),                -- AG's maser Frame, with an HUBM backplane. The PVM board is inserted in the UAM Frame.
					 fnamePvmUafm(64),               -- AG's mater Frame, with an HUBE backplane. The PVM board is inserted in the UAFM Frame.
					 fnamePvmUafs(65),               -- AG's mater Frame, with an HUBF backplane. The PVM board is inserted in the UAFS Frame.
					 fnamePvmUas(66),                -- AG's master Frame, with an HUBS backplane. The PVM board is inserted in the UAS Frame.
					 fnamePvmUamb(67),               -- AG's mater Frame, with an HUBB backplane. The PVM board is inserted in the UAMB Frame.
					 fnamePvmOnuf01D100(68),         -- AG's master Frame, with an HUBL backplane. The PVM board is inserted in the ONUF01D100 Frame.
					 fnameOnu04(262176),             -- ONU04 Frame with remote power supply
					 fnameOnu08(262177),             -- ONU08 Frame with remote power supply
-- A8010:
					 fnameA8010U18(70),              -- A8010 integrated cabinet of 18 U height
					 fnameA8010U5(71),               -- A8010 small-capacity integrated cabinet of 5 U height
-- MA5105:
					 fnameMA5105(80),                -- MA5105
					 fnameBSL(81) ,                  -- BSL
					 fnameB08(82),                   -- B08
-- MA5300:
					 fnameMA5306(83),                -- The MA5306 provides 13 horizontal slots and two power modules. Its BOM is 02000204.
					 fnameMA5300(84),                -- The MA5300 provides 16 vertical front slots, 16 vertical rear slots, and three power modules.
					 fnameS3026V(85),                -- Box-shaped S3026V Frame

					 fnameOnuf01D100H602Hublr(86),   -- RSP slave Frame, with an H602HUBL backplane
					 fnameOnuf01D100H602Hublv(87),   -- PV8 slave Frame, with an H602HUBL backplane
					 fnameAmgH602Hubl(88),           -- AMG's mater Frame, with an H602HUBL backplane
					 fnameUaH602Hubl(89),            -- UA master Frame, with an H602HUBL backplane
					 fnameHaba(90),                  -- Backplane of the UA rear-access high-density splitter mater Frame
					 fnameHabb(91),                  -- Backplane of the UA rear-access high-density integrated mater Frame
					 fnameHabd(92),                  -- Backplane of the UA front-access high-density splitter master Frame
					 fnameHabe(93),                  -- Backplane of the UA front-access high-density integrated master Frame
					 fnameHabl(94),                  -- UA front-access, high-density, small-capacity, and outdoor backplane
					 fnameHabt(95),                  -- UABT backplane
					 fnameApsbHabe(96),              -- UA front-access high-density integrated control Frame backplane, with the APSB board, as the slave Frame
					 fnameApsrHabe(97),              -- UA front-access high-density integrated control Frame backplane, with the APSR board, as the slave Frame
-- 8040:
					 fname1760(100),                 -- Quidway R1760 FRAME, 1 MIM slot and 2 SIC slot
					 fname2610(101),                 -- Quidway R2610 FRAME, 1 MIM slot and 2 SIC slot
					 fname2611(102),                 -- Quidway R2611 FRAME, 1 MIM slot and 2 SIC slot
					 fname2620(103),                 -- Quidway R2620 FRAME, 2 MIM slot
					 fname2621(104),                 -- Quidway R2621 FRAME, 2 MIM slot
					 fname2630(105),                 -- Quidway R2630 FRAME, 3 MIM slot
					 fname2631(106),                 -- Quidway R2631 FRAME, 3 MIM slot
					 fname3640(107),                 -- Quidway R3640 FRAME, 4 MIM slot
					 fname3680(108),                 -- Quidway R3680 FRAME, 8 MIM slot
-- 8060:
					 fname4620(120),                 -- Quidway R4620 FRAME, 1RPU+2IfCard+2PWR+1FAN
					 fname4640(121),                 -- Quidway R4640 FRAME, 1RPU+4IfCard+2PWR+1FAN
					 fname4680(122),                 -- Quidway R4680 FRAME, 1RPU+8IfCard+1NPU+2PWR+1FAN
					 fnameNE20-2(123),               -- Quidway NE20-2 FRAME, 1RPU+2IfCard+1NPU+2PWR+1FAN
					 fnameNE20-4(124),               -- Quidway NE20-4 FRAME, 1RPU+4IfCard+1NPU+2PWR+1FAN
					 fnameNE20-8(125),               -- Quidway NE20-8 FRAME, 1RPU+8IfCard+1NPU+2PWR+1FAN
					 fnameNE20E-4(126),              -- Quidway NE20E-4 FRAME, 2RPU+4IfCard+2NPU+2PWR+1FAN+2COP
					 fnameNE20E-8(127),              -- Quidway NE20E-8 FRAME, 2RPU+8IfCard+2NPU+2PWR+1FAN+2COP
-- 8070:
					 fnameNE05(130),                 -- Quidway NE05 FRAME, 4 VIU Slot, 1 RSU slot
					 fnameNE08(131),                 -- Quidway NE08 FRAME, 7 VIU slot, 1 RSU slot
					 fnameNE16(132),                 -- Quidway NE16 FRAME, 12 VIU slot, 2 RSU slot
					 fnameNE08E(133),                -- Quidway NE08E FRAME, 6 VIU slot, 2 RSU slot
					 fnameNE16E(134),                -- Quidway NE16E FRAME, 12 VIU slot, 2 RSU slot
-- 8011:
					 fnameNE80(140),                 -- Quidway NE80 FRAME,
					 fnameNE40-8(141),               -- Quidway NE40-8 FRAME,
					 fnameNE40-4(142),               -- Quidway NE40-4 FRAME,
					 fnameNE40-2(143),               -- Quidway NE40-2 FRAME,
-- MA
					 fnameMA5600H511upba(800),       -- The MA5600's H511UPBA backplane, with double CELLBUS and GE bus
					 fnameMa5600MA5100(801),         -- The MA5600's MA5100 backplane, on which the SCUA control board is inserted
					 fnameMa5600MA5103(802),         -- The MA5600's MA5103 backplane, on which the SCUA control board is inserted
					 fnameMa5600MA5106(803),         -- The MA5600's MA5106 backplane, on which the SCUA control board is inserted
					 fnameMa5600MA5603(804),         -- The MA5600's MA5603 backplane, on which the SCU control board is inserted
-- PVU mater Frame
					 fnamePvuMainHaba(900),          -- Rear-access PVU high density master Frame, with the H601HABA backplane
					 fnamePvuMainHabb(901),          -- Rear-access PVU high-density master Frame, with the H601HABB backplane
					 fnamePvuMainH601Habd(902),       -- Front-access PVU high-density master Frame, with the H601HABD backplane
					 fnamePvuMainHabe(903),          -- Front-access PVU high-density master Frame, with the H601HABE backplane
					 fnamePvuMainHabl(904),          -- Front-access PVU high-density master Frame, with the H601HABL backplane
					 fnamePvuMainHabt(905),          -- BT HUBT Frame

-- PVM mater Frame
					 fnamePvmMainHaba(1000),         -- Rear-access PVM high-density master Frame, with the H601HABA backplane
					 fnamePvmMainHabb(1001),         -- Rear-access PVM high-density master Frame, with the H601HABB backplane
					 fnamePvmMainHabd(1002),         -- Front-access PVM high-density master Frame, with the H601HABD backplane
					 fnamePvmMainHabe(1003),         -- Front-access PVM high-density master Frame, with the H601HABE backplane
					 fnamePvmMainHabl(1004),         -- Front-access PVM high-density master Frame, with the H601HABL backplane
					 fnamePvmMainHabt(1005),         -- BT HUBT Frame

					 frameH612MainHaba(1006),        -- Rear-access PVM high-density master Frame, with the H612HABA backplane
					 frameH612SlaveHABB(1007),       -- Rear-access PVM high-density integrated slave Frame, with the H612HABB backplane
					 frameH612MainHABD(1008),        -- Front-access PVM high-density master Frame, with the H612HABD backplane
					 frameH612SlaveHabe(1009),       -- Front-access PVM high-density integrated slave Frame, with the H612HABE backplane
					 frameH612MainHabl(1010),        -- Front-access PVM high-density master Frame, with the H612HABL backplane
					 frameH601MainHabm(1011),        -- Front-access PVM high-density master Frame, with the H601HABM backplane
					 frameH601MainHabo(1012),        -- Front-access PVM high-density master Frame, with the H601HABO backplane
					 frameH602MainHABD(196608),      -- Front-access PVM high-density master Frame, with the H612HABD backplane
					 frameH602SlaveHABE(196609),     -- Front-access PVM high-density master Frame, with the H612HABE backplane
					 frameH602SlaveHABD(196610),     -- Front-access PVM high-density master Frame, with the H612HABD backplane
					 frameH612SlaveHABD(196611),     -- Front-access PVM high-density slave Frame, with the H612HABD backplane
					 frameH612MainHABT(196612),      -- Front-access PVM high-density master Frame, with the H612HABD backplane
					 frameH612SlaveHABT(196613),     -- Front-access PVM high-density slave Frame, with the H612HABD backplane
					 frameH612SlaveHABT1(196614),    -- Front-access PVM high-density slave Frame, with the H612HABE backplane
					 frameH612MainHABA(196615),      -- Rear-access PVM high-density master Frame, with the H612HABA backplane
					 frameH612SlaveHABA(196616),     -- Rear-access PVM high-density slave Frame, with the H612HABA backplane



-- Narrowband slave shelves without the control board
					 fnamePvuSlaveHabb(1500),        -- Rear-access PVU high-density slave Frame, with the H601HABB backplane and without the master node board
					 fnamePvuSlaveH601Habe(1501),        -- Front-access PVU high-density slave Frame, with the H601HABE backplane and without the master node board
					 fnamePvuSlaveHaba(1502),        -- Rear-access PVU high-density slave Frame, with the H601HABA backplane and without the master node board
					 fnamePvuSlaveH601Habd(1503),        -- Front-access PVU high-density slave Frame, with the H601HABD backplane and without the master node board
-- RSUA slave shelves that the MD subtends
					 fnameRsuSlaveHaba(1600),             --Rear-access PVM high-density master Frame, with the H601HABA backplane
					 fnameRsuSlaveH601Habd(1601),             --Front-access PVM high-density master Frame, with the H601HABD backplane
					 fnameRsuSlaveHabl(1602),            --Front-access PVM high-density master Frame, with the H601HABL backplane
					 fnameRsuSlaveH602Habd(200706),             --Front-access PVM high-density master Frame, with the H602HABD backplane

-- MA5100
					 fnameMA5100ecua(131082),           -- The MA5100's MA5100 backplane, on which the ECUA control board is inserted
					 fnameMA5103ecua(131083),           -- The MA5100's MA5103 backplane, on which the ECUA control board is inserted
					 fnameMA5106ecua(131084),           -- The MA5100's MA5106 backplane, on which the ECUA control board is inserted
-- MA5105
					 fnameMa5605(134912)  ,           -- The MA5605, 2 U high

--  MA5200 add definitiong of frame 0x21000(135168) ~ 0x21FFF(139263)
					 fnameMA5200G2(135168),             -- Quidway MA5200G-2 FRAME,
					 fnameMA5200G4(135169),             -- Quidway MA5200G-4 FRAME,
					 fnameMA5200G8(135170),              -- Quidway MA5200G-8 FRAME,

--WA5700:
					 fnameWA5700(155648),             -- WA5700 Frame

-- MA5600
-- SCU 300mm Frame
					 fnameMA5600H801Mabv(143359),     -- Backplane(19 Inch) of the P300 new broadband master Frame: H801MABV
					 fnameMA5600H801Maba(143360),     -- Backplane of the P300 broadband master Frame: H801MABA
					 fnameMA5600H801Spba(143361),     -- Backplane of the P300 broadband SPL Frame: H801SPBA
					 fnameMA5600H801Mabh(143362),     -- Backplane(19 Inch) of the P300 new broadband master Frame: H801MABH
					 fnameMA5600H801Mabc(145949),     -- Backplane of the P300 broadband master Frame: H801MABC
					 fnameMA5600H801Mabd(145950),     -- Backplane of the P300 broadband master Frame: H801MABD
					 fnameMA5600H801Mabi(145951),     -- Backplane(19 Inch) of the P300 new broadband master Frame: H801MABI
					 fnameMA5600H802Mabc(145952),     -- Backplane of the P300 broadband master Frame: H802MABC

--MA5811S  R016C00
					 fnameMA5811SH821MABC(145953),  -- Virtual frame H821MABC of MA581S device.

-- SCU remote Frame
					 fnameMA5623AR(147526),           -- MDU device MA5623A used as remote frame
					 fnameMA5633(147527),             -- MDU device MA5633 used as remote frame

--OFA5920
					 fnameOFA5920H801MABE(145938),    -- ETSI full-specification backplane
					 fnameOFA5920H801MABB(145940),    -- 23'NEBS backplane (full-specification backplane), with rear-access line

-- MCU 300 mm Frame
					 fnameMA5600H801Mabm(143363),     -- Backplane of the MA5606T master Frame: H801MABM
					 fnameH801MABP(143446),           -- Backplane of the MA5606T master Frame: H801MABP
					 fnameMA5636(143365),             -- MA5636 outdoor Frame
-- MA5626E
					 fnameMA562XH821Mabc(143366),     -- Virtual Backplane of MA5626E Spec master Frame:H821MABC

-- MA562XP +-
					 fnameMA562XPH821Mabc(143367),    -- Virtual Frame of MA562XP Spec master Frame:H821MABC
					 fnameMA5626H821Mabc(143368),     -- Virtual Frame of MA5626(Reduce Cost)/MA5620 Spec master Frame:H821MABC
					 fnameMA5626POEH821Mabc(143451),  -- Virtual Frame of MA5626 POE Spec master Frame:H821MABC
					 fnamePvuMainH602Habd(200705),    -- Front-access PVU high-density master Frame, with the H602HABD backplane
-- OT929S
					 fnameH821MABA(143447),           -- Virtual Backplane of OT929S Spec master Frame:H821MABA
-- MA5603T
-- SCU 5 U Frame
					fnameMA5603H801Mabn(143364),     -- Backplane of the P300 broadband medium-capacity master Frame: H801MABN
					fnameMA5603H801Mabf(143369),     -- Backplane of the P300 broadband medium-capacity master Frame: H801MABF
					fnameMA5603H801Mabo(143370),     -- Backplane of the P300 broadband medium-capacity master Frame: H801MABO
					fnameMA5603H802Mabo(147523),     -- Backplane of the P300 broadband medium-capacity master Frame: H802MABO
-- MA5608T
-- SCU 2 U Frame
					fnameMA5608H801Mabr(147525),     -- Backplane of the P300 broadband medium-capacity master Frame: H801MABR
--MA5800
					fnameMA5800H901BPLB(148501),     -- Backplane of the MA5800

-- WLAN
					fnameWLANWS6603(160000),     -- Backplane of the WLAN V1R2 master Frame: WS6603
					fnameWLANWAC(160001),        -- Backplane of the WLAN V1R3 master Frame: WAC

-- SRG
					fnameSRGFWG1BKPA(190000),       -- SRG master Frame: FWG1BKPA(R1 1U)
					fnameSRGFWG2BKPA(190001),       -- SRG master Frame: FWG2BKPA(R2 1U)
					fnameSRGSU11BKPA(190002),       -- SRG master Frame: SU11BKPA(R2 2U)
					fnameSRGSU21BKPA(190003),       -- SRG master Frame: SU21BKPA(R2 3U)

-- MD
-- Narrowband slave shelves with the control board
					 fnameRspHubt(200710),           -- RSP HUBT slave Frame
					 fnamePv8Hubt(200711),           -- PV8 HUBT slave Frame
					 fnameONU60ARSUG(200712),       -- Remote indoor small-size subscriber unit, with the RSUG control board


-- UA Broadband products (204800 and after)
					 fnameApsbHaba(204810),          -- UA local rear-access high-density SPL slave Frame
					 fnameApsrHaba(204811),          -- UA remote rear-access high-density SPL slave Frame
					 fnameApsbHabd(204812),          -- UA local front-access high-density SPL salve Frame
					 fnameApsrHabd(204813),          -- UA remote front-access high-density SPL slave Frame
					 fnameApsbHabb(204814),          -- UA local rear-access high-density SPL slave Frame
					 fnameApsrHabb(204815),          -- UA remote rear-access high-density SPL slave Frame
					 fnameUa5000H612Habd(204816),    -- New BT high-density master Frame
					 fnameUa5000H612Habe(204817),    -- New BT high-density master Frame
					 fnameApsbH612Habe(204818),      -- New BT local high-density slave Frame
					 fnameH612Habl(204819),          -- UA remote rear-access high-density SPL slave Frame
					 fnameH602Habd(204820),          -- UA front-access high-density SPL master Frame, based on the H601
					 fnameH602Habe(204821),          -- UA front-access high-density integrated master Frame, based on the H601
					 fnameApsbH602Habd(204822),      -- UA local front-access high-density SPL slave Frame, based on the H601
					 fnameApsbH602Habe(204823),      -- UA local front-access high-density integrated slave Frame, based on the H601
					 fnameH601Habc(204824),          -- UA local rear-access high-density integrated master Frame
					 frameH601Habm(204825),          -- UA front-access high-density integrated master Frame
					 frameH601Habn(204826),          -- UA front-access high-density integrated master Frame

-- AG
-- PVM 300 mm Frame
					 fnameAmgH801MabaMain(262144),    -- Backplane of the P300 narrowband master Frame: H801MABA
					 fnameAmgH801MabaSlave(262145),   -- Backplane of the P300 narrowband slave Frame: H801MABA

					 --fnameOnu04(262176),               ONU04 Frame with the remote power supply
					 -- fnameOnu08(262177),               ONU08 Frame with the remote power supply
					 fnameH601Habc2(262178),           -- H601HABC Frame
					 fnameRsuHabc(262664),            -- The H601HABC Frame serves as an RSU slave Frame.
					 fnameRsuHabl(262665),            -- The H601HABL Frame serves as an RSU slave Frame.
					 fnameHwtaHib1(262666),            -- HIB Frame
					 fnameHwtaHib2(262667),            -- HIB Frame
					 fnameHwtaHib3(262668),            -- HIB Frame
-- 8031:
					 fname8031CXUNKN(536576),             -- Unknown frame
					 fname8031CX200A(536577),             -- Quidway CX200A Carrier Switch
					 fname8031CX200B(536578),             -- Quidway CX200B Carrier Switch
					 fname8031CX300A(536579),             -- Quidway CX300A Carrier Switch
					 fname8031CX300B(536580),             -- Quidway CX300B Carrier Switch
					 fname8031CX380(536581),              -- Quidway CX380 Carrier Switch
					 fname8031CX6008(536582),             -- Quidway CX600-8 Carrier Switch
					 fname8031CX60016(536583),            -- Quidway CX600-16 Carrier Switch

					 fname8031CX200C(536584),             -- Quidway CX200C Metro Service Platform

					 fname8031CX200DAC(536585),      -- Quidway CX200D-AC Metro Service Platform
					 fname8031CX200DDC(536586),      -- Quidway CX200D-DC Metro Service Platform

					 fname8031S2326PEIAC(536587),      -- Quidway S2326P-EI-AC Metro Service Platform
					 fname8031S2326PEIDC(536588),      -- Quidway S2326P-EI-DC Metro Service Platform

					 fname8031S2318PEIAC(536589),     -- Quidway S2318P-EI-AC Metro Service Platform
					 fname8031S2318PEIDC(536590),     -- Quidway S2318P-EI-DC Metro Service Platform

					 fname8031S2309PEIAC(536591),      -- Quidway S2309P-EI-AC Metro Service Platform
					 fname8031S2309PEIDC(536592),      -- Quidway S2309P-EI-DC Metro Service Platform

					 fname8031S2326PSIAC(536593),      -- Quidway S2326P-SI-AC Metro Service Platform
					 fname8031S2318PSIAC(536594),      -- Quidway S2318P-SI-AC Metro Service Platform
					 fname8031S2309PSIAC(536595),      -- Quidway S2309P-SI-AC Metro Service Platform

					 fname8031S3352PEIAC(536596),      -- Quidway S3352P-EI-AC Metro Service Platform
					 fname8031S3352PEIDC(536597),      -- Quidway S3352P-EI-DC Metro Service Platform

					 fname8031S3328TPEIAC(536598),     -- Quidway S3328TP-EI-AC Metro Service Platform
					 fname8031S3328TPEIDC(536599),      -- Quidway S3328TP-EI-DC Metro Service Platform

					 fname8031S3352PSIAC(536600),     -- Quidway S3352P-SI-AC Metro Service Platform
					 fname8031S3352PSIDC(536601),      -- Quidway S3352P-SI-DC Metro Service Platform

					 fname8031S3328TPSIAC(536602),      -- Quidway S3328TP-SI-AC Metro Service Platform
					 fname8031S3328TPSIDC(536603),      -- Quidway S3328TP-SI-DC Metro Service Platform

					 fname8031CX200DMCAC(536604),      -- Quidway CX200DMC-AC Metro Service Platform
					 fname8031CX200DMCDC(536605),     -- Quidway CX200DMC-DC Metro Service Platform

					 fname8031CX200DEAAC(536606),      -- Quidway CX200DEA-AC Metro Service Platform
					 fname8031CX200DEADC(536607),      -- Quidway CX200DEA-DC Metro Service Platform

					 fname8031CX6004(536608),            -- Quidway CX600-4 Carrier Switch

					 fname8031CX200DEAMCAC(536609),     -- Quidway CX200DEA-MC-AC Metro Service Platform
					 fname8031CX200DEAMCDC(536610),      -- Quidway CX200DEA-MC-DC Metro Service Platform

					 fname8031S3328TPEI24SAC(536611),       -- Quidway S3328TP-EI-24S-AC Metro Service Platform
					 fname8031S3328TPEI24SDC(536612),       -- Quidway S3328TP-EI-24S-DC Metro Service Platform
					 fname8031S3328TPSI24SAC(536613),       -- Quidway S3328TP-SI-24S-AC Metro Service Platform
					 fname8031S3328TPSI24SDC(536614),       -- Quidway S3328TP-SI-24S-DC Metro Service Platform

					 fname8031S3352PEI24SAC(536615),        -- Quidway S3352P-EI-24S-AC  Metro Service Platform
					 fname8031S3352PEI24SDC(536616),        -- Quidway S3352P-EI-24S-DC  Metro Service Platform

					 fname8031S3352PEI48SAC(536617),        -- Quidway S3352P-EI-48S-AC  Metro Service Platform
					 fname8031S3352PEI48SDC(536618),        -- Quidway S3352P-EI-48S-DC  Metro Service Platform
					 fname8031S3352PSI48SAC(536619),        -- Quidway S3352P-SI-48S-AC  Metro Service Platform
					 fname8031S3352PSI48SDC(536620),        -- Quidway S3352P-SI-48S-DC  Metro Service Platform

					 fname8031S2309TPEIAC(536621),        -- Quidway S2309TP-EI-AC  Metro Service Platform
					 fname8031S2309TPEIDC(536622),        -- Quidway S2309TP-EI-DC  Metro Service Platform
					 fname8031S2309TPSIAC(536623),        -- Quidway S2309TP-SI-AC  Metro Service Platform

					 fname8031S2318TPEIAC(536624),        -- Quidway S2318TP-EI-AC  Metro Service Platform
					 fname8031S2318TPEIDC(536625),        -- Quidway S2318TP-EI-DC  Metro Service Platform
					 fname8031S2318TPSIAC(536626),        -- Quidway S2318TP-SI-AC  Metro Service Platform

					 fname8031S2326TPEIAC(536627),        -- Quidway S2326TP-EI-AC  Metro Service Platform
					 fname8031S2326TPEIDC(536628),        -- Quidway S2326TP-EI-DC  Metro Service Platform
					 fname8031S2326TPSIAC(536629),        -- Quidway S2326TP-SI-AC  Metro Service Platform

					 fname8031S2352PEIAC(536630),         -- Quidway S2352P-EI-AC  Metro Service Platform
					 fname8031S2352PEIDC(536631),         -- Quidway S2352P-EI-DC  Metro Service Platform
					 fname8031CX6003DC(536632),           -- Quidway CX600-3 DC Carrier Switch
					 fname8031CX6003AC(536633),           -- Quidway CX600-3 AC Carrier Switch

					 fname8031S5328CEI(536634),         -- Quidway S5328C-EI  Metro Service Platform
					 fname8031S5328CEI24S(536635),      -- Quidway S5328C-EI-24S  Metro Service Platform
					 fname8031S5352CEI(536636),         -- Quidway S5352C-EI  Metro Service Platform
					 fname8031S5324TPSIAC(536637),         -- Quidway S5324TP-SI-AC Metro Service Platform
					 fname8031S5324TPSIDC(536638),         -- Quidway S5324TP-SI-DC Metro Service Platform
					 fname8031S5348TPSIAC(536639),         -- Quidway S5348TP-SI-AC Metro Service Platform
					 fname8031S5348TPSIDC(536640),         -- Quidway S5348TP-SI-DC Metro Service Platform
					 fname8031S5324TPPWRSI(536641),         --Quidway S5324TP-PWR-SI Metro Service Platform
					 fname8031S5348TPPWRSI(536642),         --Quidway S5348TP-PWR-SI Metro Service Platform
					 fname8031S5328CSI(536643),            -- Quidway S5328C-SI Metro Service Platform
					 fname8031S5352CSI(536644),            -- Quidway S5352C-SI Metro Service Platform
					 fname8031S5328CPWRSI(536645),         -- Quidway S5328C-PWR-SI  Metro Service Platform
					 fname8031S5352CPWRSI(536646),         -- Quidway S5352C-PWR-SI  Metro Service Platform
					 fname8031S5328CPWREI(536647),         -- Quidway S5328C-PWR-EI  Metro Service Platform
					 fname8031S5352CPWREI(536648),         -- Quidway S5352C-PWR-EI  Metro Service Platform
					 fname8031S2309TPPWREI(536649),         --Quidway S2309TP-PWR-EI Metro Service Platform
					 fname8031S2326TPPWREI(536650),         --Quidway S2326TP-PWR-EI Metro Service Platform
					 fname8031S3328TPPWREI(536651),         --Quidway S3328TP-PWR-EI Metro Service Platform
					 fname8031S3352PPWREI(536652),         -- Quidway S3352P-PWR-EI  Metro Service Platform
					 fname8031CX600X8(536653),             -- Quidway CX600-X8 Carrier Switch
					 fname8031CX600X16(536654),            -- Quidway CX600-X16 Carrier Switch
					 fname8031CX6008LCD(536655),             --Quidway CX600-8 Carrier Switch, with LCD
					 fname8031CX600X1(536656),             --Quidway CX600-X1 Carrier Switch
					 fname8031CX600X2(536657),             --Quidway CX600-X2 Carrier Switch

					 fname8031S6324C(536658),              -- Quidway S6324C  Metro Service Platform
					 fname8031S6348C(536659),              -- Quidway S6348C  Metro Service Platform
					 fname8031S5328C-HI(536660),           -- Quidway S5328C-HI  Metro Service Platform
					 fname8031S5328C-HI-24S(536661),       -- Quidway S5328C-HI-24S  Metro Service Platform
					 fname8031S5306TP-SI(536662),          -- Quidway S5306TP-SI  Metro Service Platform
					 fname8031S3326C-HI(536663),           -- Quidway S3326C-HI  Metro Service Platform

					 fname8031S2709TPEIAC(536664),        -- Quidway S2709TP-EI-AC Metro Service Platform
					 fname8031S2709TPEIDC(536665),        -- Quidway S2709TP-EI-DC Metro Service Platform
					 fname8031S2709TPSIAC(536666),        -- Quidway S2709TP-SI-AC Metro Service Platform
					 fname8031S2718TPEIAC(536667),        -- Quidway S2718TP-EI-AC Metro Service Platform
					 fname8031S2718TPEIDC(536668),        -- Quidway S2718TP-EI-DC Metro Service Platform
					 fname8031S2718TPSIAC(536669),        -- Quidway S2718TP-SI-AC Metro Service Platform
					 fname8031S2726TPEIAC(536670),        -- Quidway S2726TP-EI-AC Metro Service Platform
					 fname8031S2726TPEIDC(536671),        -- Quidway S2726TP-EI-DC Metro Service Platform
					 fname8031S2726TPSIAC(536672),        -- Quidway S2726TP-SI-AC Metro Service Platform
					 fname8031S2752PEIAC(536673),         -- Quidway S2752P-EI-AC Metro Service Platform
					 fname8031S2752PEIDC(536674),         -- Quidway S2752P-EI-DC Metro Service Platform
					 fname8031S2709TPPWREI(536675),         --Quidway S2709TP-PWR-EI Metro Service Platform
					 fname8031S2726TPPWREI(536676),         --Quidway S2726TP-PWR-EI Metro Service Platform

					 fname8031S3728TPEI24SAC(536677),       -- Quidway S3728TP-EI-24S-AC Metro Service Platform
					 fname8031S3728TPEI24SDC(536678),       -- Quidway S3728TP-EI-24S-DC Metro Service Platform
					 fname8031S3728TPEIAC(536679),     -- Quidway S3728TP-EI-AC Metro Service Platform
					 fname8031S3728TPEIDC(536680),      -- Quidway S3728TP-EI-DC Metro Service Platform
					 fname8031S3728TPSIAC(536681),      -- Quidway S3728TP-SI-AC Metro Service Platform
					 fname8031S3728TPSIDC(536682),      -- Quidway S3728TP-SI-DC Metro Service Platform
					 fname8031S3728TPPWREI(536683),         --Quidway S3728TP-PWR-EI Metro Service Platform
					 fname8031S3728TPEIMCAC(536684),         --Quidway S3728TP-EI-MC-AC Metro Service Platform

					 fname8031S3752PEIDC(536685),      -- Quidway S3752P-EI-DC Metro Service Platform
					 fname8031S3752PEIAC(536686),      -- Quidway S3752P-EI-AC Metro Service Platform
					 fname8031S3752PSIAC(536687),     -- Quidway S3752P-SI-AC Metro Service Platform
					 fname8031S3752PEI24SAC(536688),        -- Quidway S3752P-EI-24S-AC Metro Service Platform
					 fname8031S3752PEI24SDC(536689),        -- Quidway S3752P-EI-24S-DC Metro Service Platform
					 fname8031S3752PEI48SAC(536690),        -- Quidway S3752P-EI-48S-AC Metro Service Platform
					 fname8031S3752PEI48SDC(536691),        -- Quidway S3752P-EI-48S-DC Metro Service Platform
					 fname8031S3752PSI48SAC(536692),        -- Quidway S3752P-SI-48S-AC Metro Service Platform
					 fname8031S3752PSI48SDC(536693),        -- Quidway S3752P-SI-48S-DC Metro Service Platform
					 fname8031S3752PPWREI(536694),         -- Quidway S3752P-PWR-EI  Metro Service Platform

					 fname8031S5728CEIAC(536695),         -- Quidway S5728C-EI  Metro Service Platform
					 fname8031S5728CEI24SAC(536696),      -- Quidway S5728C-EI-24S  Metro Service Platform
					 fname8031S5752CEIAC(536697),         -- Quidway S5752C-EI  Metro Service Platform
					 fname8031S5728CPWREI(536698),         -- Quidway S5728C-PWR-EI Metro Service Platform
					 fname8031S5752CPWREI(536699),         -- Quidway S5752C-PWR-EI Metro Service Platform

					 fname8031S5724TPSIAC(536700),         -- Quidway S5724TP-SI-AC Metro Service Platform
					 fname8031S5724TPSIDC(536701),         -- Quidway S5724TP-SI-DC Metro Service Platform
					 fname8031S5748TPSIAC(536702),         -- Quidway S5748TP-SI-AC Metro Service Platform
					 fname8031S5748TPSIDC(536703),         -- Quidway S5748TP-SI-DC Metro Service Platform
					 fname8031S5724TPPWRSI(536704),         --Quidway S5724TP-PWR-SI Metro Service Platform
					 fname8031S5748TPPWRSI(536705),         --Quidway S5748TP-PWR-SI Metro Service Platform
					 fname8031S5728CSI(536706),            -- Quidway S5728C-SI Metro Service Platform
					 fname8031S5752CSI(536707),            -- Quidway S5752C-SI Metro Service Platform
					 fname8031S5728CPWRSI(536708),         -- Quidway S5728C-PWR-SI Metro Service Platform
					 fname8031S5752CPWRSI(536709),         -- Quidway S5752C-PWR-SI Metro Service Platform

					 fname8031S6724EI(536710),          -- Quidway S6700-24-EI  Metro Service Platform
					 fname8031S6748EI(536711),          -- Quidway S6700-48-EI  Metro Service Platform
					 fname8031CX600X1DO(536712),             --Quidway CX600-X1 Carrier Switch
					 fname8031CX600X2DO(536713),             --Quidway CX600-X2 Carrier Switch
					 fname8031CX6003DCDO(536714),           -- Quidway CX600-3 DC Carrier Switch
					 fname8031CX6003ACDO(536715),           -- Quidway CX600-3 AC Carrier Switch
					 fname8031CX600X8DO(536716),             -- Quidway CX600-X8 Carrier Switch
					 fname8031CX600X16DO(536717),            -- Quidway CX600-X16 Carrier Switch

					 fname8031S3328TPEIMC(536718),           --Quidway S3328TP-EI-MC Metro Service Platform
					 fname8031S3318TPEIMC(536719),          -- Quidway S3318TP-EI-MC Metro Service Platform
					 fname8031S3728TPEIMC(536720),           --Quidway S3728TP-EI-MC Metro Service Platform
					 fname8031S5728CHI(536721),          -- Quidway S5728C-HI  Metro Service Platform
					 fname8031S5728CHI24S(536722),       -- Quidway S5728C-HI-24S Metro Service Platform
					 fname8031S5706HI(536723),          -- Quidway S5706TP-LI-AC  Metro Service Platform
					 fname8031S3726HI(536724),       -- Quidway S3726C-HI Metro Service Platform
					 fname8031S5728PLI(536725),       -- Quidway S5700-28P-LI Metro Service Platform
					 fname8031S5728PPWRLI(536726),    -- Quidway S5700-28P-PWR-LI Metro Service Platform
					 fname8031S5752PLI(536727),       -- Quidway S5700-52P-LI Metro Service Platform
					 fname8031S5752PPWRLI(536728),    -- Quidway S5700-52P-PWR-LI Metro Service Platform
					 fname8031S5728XEI(536729),       -- Quidway S5700-28X-EI Metro Service Platform
					 fname8031S5752XEI(536730),       -- Quidway S5700-52X-EI Metro Service Platform
					 fname8031S5352CPWREIB(536770),   --Quidway S5300-28C-PWR-EI Metro Service Platform
					 fname8031S5328CPWREIB(536771),   --Quidway S5300-52C-PWR-EI Metro Service Platform
					 fname8031S5328PLI(536772),       -- Quidway S5300-28P-LI Metro Service Platform
					 fname8031S5352PLI(536773),       -- Quidway S5300-52P-LI Metro Service Platform
					 fname8031S5728PLIDC(536774),       -- Quidway S5700-28P-LI-DC Metro Service Platform
					 fname8031S5752PLIDC(536775),       -- Quidway S5700-52P-LI-DC Metro Service Platform
					 fname8031S5328PLIDC(536776),   --Quidway S5300-28P-LI-DC Metro Service Platform
					 fname8031S5352PLIDC(536777),   --Quidway S5300-52P-LI-DC Metro Service Platform
					 fname8031S57S28PLIAC(536778),   -- Quidway S5700S-28P-LI-AC Metro Service Platform
					 fname8031S57S52PLIAC(536779),   -- Quidway  S5700S-52P-LI-AC Metro Service Platform

					 fname8031S271052PSI(536780),        -- Quidway S2710S-52P-SI Metro Service Platform
					 fname8031S271026TPPWRSI(536781),    -- Quidway S2710-26TP-PWR-SI Metro Service Platform
					 fname8031S271052PPWRSI(536782),    -- Quidway S2710-52P-PWR-SI Metro Service Platform
					 fname8031S270052PPWREI(536783),    -- Quidway S2700-52P-PWR-EI Metro Service Platform
					 fname8031S370052PPWRSI(536784),    -- Quidway S3700-28TP-PWR-SI Metro Service Platform
					 fname8031S370028TPPWRSI(536785),    -- Quidway S3700-52P-PWR-SI Metro Service Platform
					 fname8031S571028CPWRLI(536786),    -- Quidway S5710-28C-PWR-LI Metro Service Platform
					 fname8031S571052CPWRLI(536787),    -- Quidway S5710-52C-PWR-LI Metro Service Platform
					 fname8031S571028CLI(536788),    -- Quidway S5710-28C-LI  Metro Service Platform
					 fname8031S571052CLI(536789),    -- Quidway S5710-52C-LI  Metro Service Platform
					 fname8031S5710PLIAC(536790),    -- Quidway S5700-10P-LI-AC Metro Service Platform
					 fname8031S5710PPWRLIAC(536791),    -- Quidway S5700-10P-PWR-LI-AC Metro Service Platform
					 fname8031S5726XSI12SAC(536792),    -- Quidway S5700-26X-SI-12S-AC Metro Service Platform
					 fname8031S5728XLIAC(536793),    -- Quidway S5700-28X-LI-AC Metro Service Platform
					 fname8031S5728XLIDC(536794),    -- Quidway S5700-28X-LI-DC Metro Service Platform
					 fname8031S5752XLIAC(536795),    -- Quidway S5700-52X-LI-AC Metro Service Platform
					 fname8031S5752XLIDC(536796),    -- Quidway S5700-52X-LI-DC Metro Service Platform
					 fname8031S5728XPWRLIAC(536797),              -- Quidway S5700-28X-PWR-LI-AC Metro Service Platform
					 fname8031S5752XPWRLIAC(536798),              -- Quidway S5700-52X-PWR-LI-AC Metro Service Platform
					 fname8031S5710108CPWRHIAC(536799),           -- Quidway S5710-108C-PWR-HI-AC Metro Service Platform
					 fname8031S5710108CHIAC(536800),              -- Quidway S5710-108C-HI-AC Metro Service Platform
					 fname8031S6348CE6000(536801),                -- Quidway S6348C_E6000 Metro Service Platform
					 fname8031S571028CPWREI(536802),              -- Quidway S5710-28C-PWR-EI Metro Service Platform
					 fname8031S571052CPWREI(536803),              -- Quidway S5710-52C-PWR-EI Metro Service Platform
					 fname8031S5310PLIAC(536804),                 -- Quidway S5300-10P-LI-AC Metro Service Platform
					 fname8031S531028CEI(536805),                 -- Quidway S5310-28C-EI Metro Service Platform
					 fname8031S531052CEI(536806),                 -- Quidway S5310-52C-EI Metro Service Platform
					 fname8031S2328PEIAC(536807),                 -- Quidway S2328P-EI-AC Metro Service Platform
					 fname8031S275026TPPWREIAC(536808),           -- Quidway S2750-26TP-PWR-EI-AC Metro Service Platform
					 fname8031S235026TPPWREIAC(536809),           -- Quidway S2350-26TP-PWR-EI-AC Metro Service Platform
					 fname8031S275126TPPWREIAC(536810),           -- Quidway S2751-26TP-PWR-EI-AC Metro Service Platform
					 fname8031S235028TPEIAC(536811),              -- Quidway S2350-28TP-EI-AC Metro Service Platform
					 fname8031S275028TPEIAC(536812),              -- Quidway S2750-28TP-EI-AC Metro Service Platform
					 fname8031S235018TPPWREIAC(536813),           -- Quidway S2350-18TP-PWR-EI-AC Metro Service Platform
					 fname8031S275018TPPWREIAC(536814),           -- Quidway S2750-18TP-PWR-EI-AC Metro Service Platform
					 fname8031S330052PEI(536815),                 -- Quidway S3300-52P-EI Metro Service Platform
					 fname8031CX600-X1-M4(536816),                --Quidway CX600-X1-M4 Carrier Switch for V8R5
					 fname8031CX600-X2-M8(536817),                --Quidway CX600-X2-M8 Carrier Switch for V8R5,AC. compatitable with old panel, no "AC" in name
					 fname8031CX600-M4-DO(536818),             --Quidway CX600-X1-M4 Carrier Switch for V8R5,overseas
					 fname8031CX600-M8-DO(536819),             --Quidway CX600-X2-M8 Carrier Switch for V8R5,AC,overseas.  compatitable with old panel, no "AC" in name
					 fname8031CX600-X2-M16(536820),               --Quidway CX600-X2-M16 Carrier Switch for V8R5
					 fname8031CX600-M16-DO(536821),            --Quidway CX600-X2-M16 Carrier Switch for V8R5,overseas
					 fname8031S5700-28X-LI-24S-DC(536822),        --S5700-28X-LI-24S-DC Mainframe(20 GE SFP,4 GE Combo,4 10GE SFP+,DC -48V)
					 fname8031S5300-28X-LI-24S-DC(536823),        --S5300-28X-LI-24S-DC Mainframe(20 GE SFP,4 GE Combo,4 10GE SFP+,DC -48V)
					 fname8031S5700-28X-LI-24S-AC(536824),        --S5700-28X-LI-24S-AC Mainframe(20 GE SFP,4 GE Combo,4 10GE SFP+,AC 110/220V)
					 fname8031S5300-28X-LI-24S-AC(536825),        --S5300-28X-LI-24S-AC Mainframe(20 GE SFP,4 GE Combo,4 10GE SFP+,AC 110/220V)
					 fname8031S5300-28X-LI-DC(536826),            --5300-28X-LI-DC Mainframe(24 GE RJ45,4 10GE SFP+,DC -48V)
					 fname8031S5300-28X-LI-AC(536827),            --S5300-28X-LI-AC Mainframe(24 GE RJ45,4 10GE SFP+,AC 110/220V)
					 fname8031S2750-28TP-PWR-EI-AC(536828),       --S2750-28TP-PWR-EI-AC Mainframe(24 FE RJ45,2 GE SFP,2 GE COMBO,PoE,AC 110/220V)
					 fname8031S2350-28TP-PWR-EI-AC(536829),       --S2350-28TP-PWR-EI-AC  Mainframe(24 FE RJ45,2 GE SFP,2 GE COMBO,PoE,AC 110/220V)
					 fname8031S2751-28TP-PWR-EI-AC(536830),       --S2751-28TP-PWR-EI-AC  Mainframe(24FE RJ45,2 GE SFP,2 GE COMBO,12 PoE,AC 110/220V)
					 fname8031S2350-20TP-PWR-EI-AC(536831),       --S2350-20TP-PWR-EI-AC Mainframe(16 FE RJ45,2 GE SFP,2 GE COMBO,PoE,AC 110/220V)
					 fname8031S2750-20TP-PWR-EI-AC(536832),       --S2750-20TP-PWR-EI-AC Mainframe(16 FE RJ45,2 GE SFP,2 GE COMBO,PoE,AC 110/220V)
					 fname8031S2350-28TP-EI-AC(536833),           --S2350-28TP-EI-AC Mainframe(24 FE RJ45,2 GE SFP,2 GE COMBO,AC 110/220V)
					 fname8031S2750-28TP-EI-AC(536834),           --S2750-28TP-EI-AC  Mainframe(24 FE RJ45,2 GE SFP,2 GE COMBO,AC 110/220V)
					 fname8031S3700-28TP-EI-24S-DC(536835),       -- S3700-28TP-EI-24S-DC
					 fname8031CX600-X2-M8-DC(536836),             --Quidway CX600-X2-M8 Carrier Switch for V8R5,DC
					 fname8031CX600-X2-M8-DC-DO(536837),          --Quidway CX600-X2-M8 Carrier Switch for V8R5,DC,overseas

					 fname8031S5701-28X-LI-AC(536838),            --S5701-28X-LI-AC       Metro Service Platform for V2R3C00
					 fname8031S5701-28X-LI-24S-AC(536839),        --S5701-28X-LI-24S-AC   Metro Service Platform for V2R3C00
					 fname8031S5700-28P-LI-BAT(536840),           --S5700-28P-LI-BAT      Metro Service Platform for V2R3C02
					 fname8031S5700-28P-LI-4AH(536841),           --S5700-28P-LI-4AH      Metro Service Platform for V2R3C02
					 fname8031S5700-28P-LI-24S-BAT(536842),       --S5700-28P-LI-24S-BAT  Metro Service Platform for V2R3C02
					 fname8031S5700-28P-LI-24S-4AH(536843),       --S5700-28P-LI-24S-4AH  Metro Service Platform for V2R3C02
					 fname8031S5300-28P-LI-BAT(536844),           --S5300-28P-LI-BAT      Metro Service Platform for V2R3C02
					 fname8031S5300-28P-LI-4AH(536845),           --S5300-28P-LI-4AH      Metro Service Platform for V2R3C02
					 fname8031S5300-28P-LI-24S-BAT(536846),       --S5300-28P-LI-24S-BAT  Metro Service Platform for V2R3C02
					 fname8031S5300-28P-LI-24S-4AH(536847),       --S5300-28P-LI-24S-4AH  Metro Service Platform for V2R3C02
					 fname8031S5700-28X-LI-24CS-AC(536848),       --S5700-28X-LI-24CS-AC  Metro Service Platform for V2R3C02
					 fname8031S5700-28X-LI-24CS-DC(536849),       --S5700-28X-LI-24CS-DC  Metro Service Platform for V2R3C02
					 fname8031S5300-28X-LI-24CS-AC(536850),       --S5300-28X-LI-24CS-AC  Metro Service Platform for V2R3C02
					 fname8031S5300-28X-LI-24CS-DC(536851),       --S5300-28X-LI-24CS-DC  Metro Service Platform for V2R3C02

					 fname8031S5310-108C-PWR-HI(536852),          --S5310-108C-PWR-HI     Metro Service Platform for V2R5C00
					 fname8031S5300-10P-PWR-LI-AC(536853),        --S5300-10P-PWR-LI-AC   Metro Service Platform for V2R5C00
					 fname8031S5300-28P-PWR-LI-AC(536854),        --S5300-28P-PWR-LI-AC   Metro Service Platform for V2R5C00
					 fname8031S5300-52P-PWR-LI-AC(536855),        --S5300-52P-PWR-LI-AC   Metro Service Platform for V2R5C00
					 fname8031S5300-52X-LI-AC(536856),            --S5300-52X-LI-AC       Metro Service Platform for V2R5C00
					 fname8031S5300-52X-LI-DC(536857),            --S5300-52X-LI-DC       Metro Service Platform for V2R5C00
					 fname8031S5300-28X-PWR-LI-AC(536858),        --S5300-28X-PWR-LI-AC   Metro Service Platform for V2R5C00
					 fname8031S5300-52X-PWR-LI-AC(536859),        --S5300-52X-PWR-LI-AC   Metro Service Platform for V2R5C00
					 fname8031S2350-28TP-EI-DC(536860),           --S2350-28TP-EI-DC      Metro Service Platform for V2R5C00
					 fname8031S5700-28TP-LI-AC(536861),           --S5700-28TP-LI-AC      Metro Service Platform for V2R3C10
					 fname8031S5700-28TP-PWR-LI-AC(536862),       --S5700-28TP-PWR-LI-AC  Metro Service Platform for V2R3C10
					 fname8031S5701-28TP-PWR-LI-AC(536863),       --S5701-28TP-PWR-LI-AC  Metro Service Platform for V2R3C10
					 fname8090CX600-X8A(536864),            		   --Quidway CX600-X8A Carrier Switch
					 fname8090CX600-X16A(536865),            	   --Quidway CX600-X16A Carrier Switch
					 fname8031S5720-56C-HI-AC(536866),            --S5720-56C-HI-AC       Metro Service Platform for V2R6C00
					 fname8031S5720-56C-PWR-HI-AC(536867),        --S5720-56C-PWR-HI-AC   Metro Service Platform for V2R6C00
					 fname8031S5720-32C-HI-24S-AC(536868),        --S5720-32C-HI-24S-AC   Metro Service Platform for V2R6C00
					 fname8090CX600-X8A-DC(536869),               --Quidway CX600-X8A-DC Carrier Switch
					 fname8090CX600-X16A-DC(536870),              --Quidway CX600-X16A-DC Carrier Switch
					 fname8031CX600-M2E(536871),		               --Quidway CX600-M2E Carrier Switch for V8R5
					 fname8031CX600-M2F(536872),		               --Quidway CX600-M2F Carrier Switch for V8R5
					 fname8031S1720-28GFR-4TP(536873),            --S1720-28GFR-4TP   Metro Service Platform for V2R6C10
					 fname8031S1720-20GFR-4TP(536874),            --S1720-20GFR-4TP   Metro Service Platform for V2R6C10
					 fname8031S2720-28TP-EI-AC(536875),           --S2720-28TP-EI-AC  Metro Service Platform for V2R6C10

					 fname8031S5720-36C-EI-28S-AC(536876),        --S5720-36C-EI-28S-AC   Metro Service Platform for V2R7C00
					 fname8031S5320-36C-EI-28S-AC(536877),        --S5320-36C-EI-28S-AC   Metro Service Platform for V2R7C00
					 fname8031S5320-36C-EI-28S-DC(536878),        --S5320-36C-EI-28S-DC   Metro Service Platform for V2R7C00
					 fname8031S5720-56C-EI-48S-AC(536879),        --S5720-56C-EI-48S-AC   Metro Service Platform for V2R7C00
					 fname8031S5320-56C-EI-48S-AC(536880),        --S5320-56C-EI-48S-AC   Metro Service Platform for V2R7C00
					 fname8031S5320-56C-EI-48S-DC(536881),        --S5320-56C-EI-48S-DC   Metro Service Platform for V2R7C00
					 fname8031S5720-36C-EI-AC(536882),            --S5720-36C-EI-AC       Metro Service Platform for V2R7C00
					 fname8031S5320-36C-EI-AC(536883),            --S5320-36C-EI-AC       Metro Service Platform for V2R7C00
					 fname8031S5320-36C-EI-DC(536884),            --S5320-36C-EI-DC       Metro Service Platform for V2R7C00
					 fname8031S5720-36PC-EI-AC(536885),           --S5720-36PC-EI-AC      Metro Service Platform for V2R7C00
					 fname8031S5320-36PC-EI-AC(536886),           --S5320-36PC-EI-AC      Metro Service Platform for V2R7C00
					 fname8031S5320-36PC-EI-DC(536887),           --S5320-36PC-EI-DC      Metro Service Platform for V2R7C00
					 fname8031S5720-56C-EI-AC(536888),            --S5720-56C-EI-AC       Metro Service Platform for V2R7C00
					 fname8031S5320-56C-EI-AC(536889),            --S5320-56C-EI-AC       Metro Service Platform for V2R7C00
					 fname8031S5320-56C-EI-DC(536890),            --S5320-56C-EI-DC       Metro Service Platform for V2R7C00
					 fname8031S5720-56PC-EI-AC(536891),           --S5720-56PC-EI-AC      Metro Service Platform for V2R7C00
					 fname8031S5320-56PC-EI-AC(536892),           --S5320-56PC-EI-AC      Metro Service Platform for V2R7C00
					 fname8031S5320-56PC-EI-DC(536893),           --S5320-56PC-EI-DC      Metro Service Platform for V2R7C00
					 fname8031S5720-36C-PWR-EI-AC(536894),        --S5720-36C-PWR-EI-AC   Metro Service Platform for V2R7C00
					 fname8031S5320-36C-PWR-EI-AC(536895),        --S5320-36C-PWR-EI-AC   Metro Service Platform for V2R7C00
					 fname8031S5320-36C-PWR-EI-DC(536896),        --S5320-36C-PWR-EI-DC   Metro Service Platform for V2R7C00
					 fname8031S5720-56C-PWR-EI-AC(536897),        --S5720-56C-PWR-EI-AC   Metro Service Platform for V2R7C00
					 fname8031S5320-56C-PWR-EI-AC(536898),        --S5320-56C-PWR-EI-AC   Metro Service Platform for V2R7C00
					 fname8031S5720-56C-PWR-EI-AC1(536899),       --S5720-56C-PWR-EI-AC1  Metro Service Platform for V2R7C00
					 fname8031S5720-32X-EI-24S-AC(536900),        --S5720-32X-EI-24S-AC   Metro Service Platform for V2R7C00
					 fname8031S5320-32X-EI-24S-AC(536901),        --S5320-32X-EI-24S-AC   Metro Service Platform for V2R7C00
					 fname8031S5320-32X-EI-24S-DC(536902),        --S5320-32X-EI-24S-DC   Metro Service Platform for V2R7C00
					 fname8031S5720-50X-EI-46S-AC(536903),        --S5720-50X-EI-46S-AC   Metro Service Platform for V2R7C00
					 fname8031S5320-50X-EI-46S-AC(536904),        --S5320-50X-EI-46S-AC   Metro Service Platform for V2R7C00
					 fname8031S5320-50X-EI-46S-DC(536905),        --S5320-50X-EI-46S-DC   Metro Service Platform for V2R7C00
					 fname8031S5720-32X-EI-AC(536906),            --S5720-32X-EI-AC       Metro Service Platform for V2R7C00
					 fname8031S5320-32X-EI-AC(536907),            --S5320-32X-EI-AC       Metro Service Platform for V2R7C00
					 fname8031S5320-32X-EI-DC(536908),            --S5320-32X-EI-DC       Metro Service Platform for V2R7C00
					 fname8031S5720-32P-EI-AC(536909),            --S5720-32P-EI-AC       Metro Service Platform for V2R7C00
					 fname8031S5320-32P-EI-AC(536910),            --S5320-32P-EI-AC       Metro Service Platform for V2R7C00
					 fname8031S5320-32P-EI-DC(536911),            --S5320-32P-EI-DC       Metro Service Platform for V2R7C00
					 fname8031S5720-52X-EI-AC(536912),            --S5720-52X-EI-AC       Metro Service Platform for V2R7C00
					 fname8031S5320-52X-EI-AC(536913),            --S5320-52X-EI-AC       Metro Service Platform for V2R7C00
					 fname8031S5320-52X-EI-DC(536914),            --S5320-52X-EI-DC       Metro Service Platform for V2R7C00
					 fname8031S5720-52P-EI-AC(536915),            --S5720-52P-EI-AC       Metro Service Platform for V2R7C00
					 fname8031S5320-52P-EI-AC(536916),            --S5320-52P-EI-AC       Metro Service Platform for V2R7C00
					 fname8031S5320-52P-EI-DC(536917),            --S5320-52P-EI-DC       Metro Service Platform for V2R7C00
					 fname8031S5720-50X-EI-AC(536918),            --S5720-50X-EI-AC       Metro Service Platform for V2R7C00
					 fname8031S5320-50X-EI-AC(536919),            --S5320-50X-EI-AC       Metro Service Platform for V2R7C00
					 fname8031S5320-50X-EI-DC(536920),            --S5320-50X-EI-DC       Metro Service Platform for V2R7C00



-- 8090:
					 fname8090Unknown(561152),            -- Quidway unknown FRAME,
					 fname8090Whole(561153),              -- Quidway NE80E FRAME, NE5000E FRAME,
					 fname8090Half(561154),              -- Quidway NE40E FRAME,
					 fname8090HalfLow(561155),            -- Quidway Ne40E FRAME low ,40E
					 fname8090BTBMaster(561156),          -- Quidwy NE5000E BTB MASTER FRAME
					 fname8090BTBSlave(561157),           -- Quidwy NE5000E BTB Slave FRAME
					 fname8090ClusterCentral(561158),     -- Quidwy NE5000E Cluster Central FRAME
					 fname8090ClusterLine(561159),        -- Quidwy NE5000E Cluster Line  FRAME
					 fname8090Quarter(561160),            -- Quidwy Ne40E-4 FRAME
					 fname8090NE40E3DC(561161),          -- Quidwy Ne40E-3 FRAME
					 fname8090NE40E3AC(561162),          -- Quidwy Ne40E-3 FRAME
					 fname8090HalfX(561163),              -- Quidway NE40E-X8 FRAME,
					 fname8090WholeX(561164),             -- Quidway NE80E-X16 FRAME,
					 fname8090NE5000EX(561165),          --Quidway NE5000E-X16 FRAME,
					 fname8090NE40EX1(561166),           --Quidway NE40E-X1 FRAME,
					 fname8090NE40EX2(561167),           --Quidway NE40E-X2 FRAME,
					 fname8090NE5000EX-VB(561168),       --Quidway NE5000E-X16VB FRAME,
					 fname8090NE40E-X2-M8(561169),       --Quidway CX600-X2-M8 FRAME,ne40e,AC. compatitable with old panel, no "AC" in name
					 fname8090NE40E-X1-M4(561170),       -- Quidway CX600-X1-M4 FRAME, ne40e
					 fname8090NE40E-X2-M16(561171),      --Quidway CX600-X2-M16 FRAME, ne40e
					 fname8090CX600-X2(561172),          --Quidway CX600-X2 FRAME,
					 fname8090NE5000EX-A(561173),        --Quidway NE5000E-X16A FRAME,
					 fname8090NE5000ENGCCC(561174),      --Quidway NE5000E-NGCCC FRAME,
					 fname8090NE40E-X16A(561175),        --Quidway NE40E-X16A FRAME,    ----added by xuelu for X16A 2013.5.10
					 fname8090NE40E-X2-M8-DC(561176),       --Quidway CX600-X2-M8 FRAME,ne40e,DC
					 fname8090NE40E-X8A(561177),          --Quidway NE40E-X8A FRAME,
					 fname8090NE5000E-X8A(561178),        --Quidway NE5000E-X8A FRAME,
					 fname8090NE40E-X8A-DC(561179),         --Quidway NE40E-X8A-DC FRAME,
	 fname8090NE40E-X16A-DC(561180),        --Quidway NE40E-X16A-DC FRAME,
					 fname8090NE5000E-X8(562031),       --Quidway NE5000E-X8 FRAME,
					 fname8090NE40E-M2E(562032),       --Quidway NE40E-M2E FRAME,
					 fname8090NE40E-M2F(562033),       --Quidway NE40E-M2F FRAME,

--MA5611S  R015C10
					 frameMA5611SAE08(561221),      -- Virtual frame MA5611S-AE08 of MA5611S(sd5130) FTTS device.
-- ME60:
					 fnameME60Unknown(159744),           -- Quidway unknown FRAME,
					 fnameME60Whole(159745),            -- Quidway ME60-16 FRAME,
					 fnameME60Half(159746),             -- Quidway ME60-8 FRAME,
					 fnameME60HalfLow(159747),               -- Quidway ME60-8 FRAME,
					 fnameME60WholeBKPC(159748),             -- Quidway ME60-16 FRAME
					 fnameME60Quarter(159749),                -- Quidway ME60-4 FRAME
					 fnameME60X3DC(159750),              -- Quidway ME60-X3 FRAME
					 fnameME60X3AC(159751),              -- Quidway ME60-X3 FRAME
					 fnameME60X8(159752),                -- Quidway ME60-X8  FRAME
					 fnameME60X16(159753),               -- Quidway ME60-X16 FRAME
					 fnameME60X8A(159754),                --ME60-X8A Integrated Chassis AC Components
					 fnameME60X8A-DC(159755),             --ME60-X8A Integrated Chassis DC Components
					 fnameME60X16A(159756),                -- ME60-X16A Integrated AC Chassis Components
					 fnameME60X16A-DC(159757),              --ME60-X16A Integrated DC Chassis Components

-- S9300:       0x000A1000~0x000A1fff(659456~663551)
					 fnameLE0KS9303(659456),                -- Quidway S9303 FRAME
					 fnameLE0KS9306(659457),                -- Quidway S9306 FRAME
					 fnameLE0KS9312(659458),                -- Quidway S9312 FRAME
					 fnameLE0110(659459),                -- Quidway S9310 FRAME
					 fnameLE0203Poe(659460),             -- Quidway S9303 POE FRAME
					 fnameLE0BS9306P1(659461),             -- Quidway S9306 POE FRAME
					 fnameLE02WMMPA(659462),
					 fnameLE0BS9312P1(659463),             -- Quidway S9312 POE FRAME
					 fnameLE02Spu(659464),               -- Quidway S9300 SPU FRAME
					 fnameLE2BS9303E00(659465),               -- Quidway S9303E FRAME
					 fnameLE2BS9306E00(659466),               -- Quidway S9306E FRAME
					 fnameLE2BS9312E00(659467),               -- Quidway S9312E FRAME
					 fnameLE2BS9303E01(659468),               -- Quidway S9303E_01 FRAME
					 fnameLE2BS9306E01(659469),               -- Quidway S9306E_01 FRAME
					 fnameLE2BS9312E01(659470),               -- Quidway S9312E_01 FRAME

-- S7700:       0x000A2000~0x000A2fff(663552~667647)
					 fnameES0B00770300(663552),                -- Quidway S7703 FRAME
					 fnameES0B00770600(663553),                -- Quidway S7706 FRAME
					 fnameES0B00771200(663554),                -- Quidway S7712 FRAME
					 fnameES0203Poe(663555),             -- Quidway S7703 POE FRAME
					 fnameES0B017706P0(663556),             -- Quidway S7706 POE FRAME
					 fnameES0B017712P0(663557),             -- Quidway S7712 POE FRAME
					 fnameES02Spu(663558),               -- Quidway S7700 SPU FRAME
					 fnameES1B00770301(663559),          -- Quidway S7703 FRAME FCC
					 fnameES1B00770601(663560),          -- Quidway S7706 FRAME FCC
					 fnameES1B00771201(663561),          -- Quidway S7712 FRAME FCC
					 fnameES1B017706P1(663562),          -- Quidway S7706 POE FRAME FCC
					 fnameES1B017712P1(663563),          -- Quidway S7712 POE FRAME FCC

-- S9700:       0x000A7000~0x000A7fff(684032~688127)
					 fnameEH1BS9703E00(684032),                -- Quidway S9703 FRAME
					 fnameEH1BS9706E00(684033),                -- Quidway S9706 FRAME
					 fnameEH1BS9712E00(684034),                -- Quidway S9712 FRAME
					 fnameEH02Spu(684035),                     -- Quidway S9700 SPU FRAME

-- S12700:      0x000AB000~0x000ABfff(700416~704511)
					 fnameET1D2S1270800(700416),              -- HUAWEI S12708 FRAME
					 fnameET1D2S1271200(700417),              -- HUAWEI S12712 FRAME

-- NSE:
					 fnameNSEUnknown(570152),            -- Quidway unknown FRAME,
					 fnameSSPHalf(570154),                       -- Quidway SSP1000 FRAME
					 fnameSSPWhole(570155),                   -- Quidway SSP2000 FRAME
					 fnameSSPNE5000E(570156),             -- Quidway SSP3000 FRAME
					 fnameNSEQuarter(570157),                -- Quidway NSE1000-4 FRAME
					 fnameNSEHalf(570158),                    -- Quidway NSE1000-8 FRAME
					 fnameSSP5000X8(696322),              -- Quidway SSP5000X8 FRAME
					 fnameSSP5000X16(696321),             -- Quidway SSP5000X16 FRAME

-- ATN:
					 fnameATNUnknown(225280),           -- ATN unknown FRAME,
					 fnameATNDEV980(225281),            -- ATN 980 FRAME,
					 fnameATNDEV990(225282),            -- ATN 990 FRAME,

--ATN 910&950,950B
--chassis
					fnameATNDEV910(225283),          --ATN910 chassis
					fnameATNDEV950(225284),           --ATN950 chassis
					fnameATNDEV950B(225285),          --ATN950B chassis
					fnameATNDEV910IA(225483),          --910I AC chassis
					fnameATNDEV910IB(225494),          --910I DC chassis
					fnameATNDEV910IC(225495),          --910I-C AC chassis
					fnameATNDEV910ID(225496),          --910I-TC DC chassis
					fnameATNDEV910IE(225515),          --910I-AC poe chassis
					fnameATNDEV905A(225508),           --905-AC indoor chassis
					fnameATNDEV905B(225509),           --905-AC outdoor chassis
					fnameATNDEV905C(225510),           --905-AC outdoor poe chassis
-- PTN:
					fnamePTNUnknown(229376),                  --Unknown chassis type
					fnamePTN6900Half(229377),                 --PTN6900-8 chassis
					fnamePTN6900Whole(229378),                 --PTN6900-16 chassis
					-- for VDF
					fnamePTN6900TNRZ1BKPE(229379),      --Integrated DC Chassis Components (PTN 6900-3)
					fnamePTN6900TNRK003BKP01(229380),   --Integrated AC Chassis Components (PTN 6900-3)
					fnamePTN6900TNRB0BKP0270(229381),   --PTN 6900-2 Integrated Chassis Components
					fnamePTN6900TNRB0BKP0170(229382),   --PTN 6900-1 Integrated Chassis Components
			 --for V8 CX600 packaging
			 fnamePTN6900TNRB0BKP0171(229383),   --PTN 6900-1-M4 Integrated Chassis Components
			 fnamePTN6900TNRB0BKP0271(229384),   --PTN 6900-2-M8 Integrated DC Chassis Components
			 fnamePTN6900TNRB0BKP0273(229385),   --PTN 6900-2-M8 Integrated AC Chassis Components
			 fnamePTN6900TNRB0BKP0272(229386),   --PTN 6900-2-M16 Integrated Chassis Components
			  fnamePTN6900-M2E(229389),            --PTN 6900-M2E Integrated Chassis Components
			  fnamePTN6900-M2F(229390),            --PTN 6900-M2F Integrated Chassis Components

			 --for PTN7900 V100R006C00 2013-8-8 by lishaobin begin
					fnamePTN7900TPA1AFBTBKP00A(229387),   --PTN 7900-32 Integrated Chassis Components
					fnamePTN7900TPB1AFBTBKP00A(229388),   --PTN 7900-24 Integrated Chassis Components
			 --for PTN7900 V100R006C00 2013-8-8 by lishaobin end
					fnamePTN6900-8A(229391),            --PTN 6900-8A Integrated Chassis AC Components
					fnamePTN6900-8A-DC(229392),         --PTN 6900-8A Integrated Chassis DC Components
					fnamePTN6900-16A(229393),            --PTN 6900-16A Integrated AC Chassis Components
					fnamePTN6900-16A-DC(229394),         --PTN 6900-16A Integrated DC Chassis Components

-- AR:          0x000A3000~0x000A3fff(667648~671743)
					 fnameAR1220(667648),           -- Quidway AR1220 FRAME
					 fnameAR1220W(667649),          -- Quidway AR1220W FRAME
					 fnameAR1240(667650),           -- Quidway AR1240 FRAME
					 fnameAR1240W(667651),          -- Quidway AR1240W FRAME
					 fnameAR2220(667652),           -- Quidway AR2220 150W AC Power FRAME
					 fnameAR2240(667653),           -- Quidway AR2240 350W AC Power,Router Unit 40 FRAME
					 fnameAR3260(667654),           -- Quidway AR3260 350W AC Power,Router Unit 80 FRAME
					 fnameAR1220V(667655),          -- Quidway AR1220V POE FRAME
					 fnameAR201(667656),            -- Quidway AR201 FRAME
					 fnameAR206(667657),            -- Quidway AR206 FRAME
					 fnameAR207(667658),            -- Quidway AR207 FRAME
					 fnameAR207V(667659),           -- Quidway AR207V FRAME
					 fnameAR208(667660),            -- Quidway AR208 FRAME
					 fnameAR1220VW(667661),         -- Quidway AR1220VW FRAME
					 fnameAR1220S(667662),          -- Quidway AR1220S FRAME
					 fnameAR1220WS(667663),         -- Quidway AR1220WS FRAME
					 fnameAR207VP(667671),          -- Quidway AR207VP FRAME
					 fnameAR201S(667672),           -- Quidway AR201S FRAME
					 fnameAR207S(667673),           -- Quidway AR207S FRAME
					 fnameAR151(667674),            -- Quidway AR151 FRAME
					 fnameAR157(667675),            -- Quidway AR157 FRAME
					 fnameAR2220S(667676),          -- Quidway AR2220S FRAME
					 fnameAR1220L(667677),          -- Quidway AR1220L FRAME
					 fnameAR207GHSPA(667678),       -- Quidway AR207G-HSPA+7 FRAME
					 fnameSRG1320V(667679),         -- Quidway SRG1320V FRAME
					 fnameSRG1320VW(667680),        -- Quidway RG1320VW FRAME
					 fnameSRG2320(667681),          -- Quidway SRG2320 FRAME
					 fnameSRG3340(667682),          -- Quidway SRG3340 FRAME
					 fnameSRG3360(667683),          -- Quidway SRG3360 FRAME
					 fnameAR156(667684),            -- Quidway AR156 FRAME
					 fnameAR158E(667685),           -- Quidway AR158E FRAME
					 fnameAR151GHSPA(667686),       -- Quidway AR151G-HSPA+7 FRAME
					 fnameAR157GHSPA(667687),       -- Quidway AR157G-HSPA+7 FRAME
					 fnameAR151WP(667688),          -- Quidway AR151W-P FRAME
					 fnameAR157W(667689),           -- Quidway AR157W FRAME
					 fnameAR1220D(667690),          -- Quidway AR158EGVW-HSPA+7-P FRAME
					 fnameAR157VW(667691),          -- Quidway AR157VW FRAME
					 fnameAR158EVW(667692),         -- Quidway AR158EVW FRAME
					 fnameAR220148FE(667693),       -- Quidway AR2201-48FE FRAME
					 fnameAR220248FE(667694),       -- Quidway AR2202-48FE FRAME
					 fnameAR2220L(667695),          -- Quidway AR2220L FRAME
					 fnameAR201VWP(667696),         -- Quidway AR201VWP FRAME
					 fnameAR207VW(667697),         -- Quidway AR207VW FRAME
					 fnameAR2230(667698),         -- Quidway AR2230 FRAME
					 fnameAR2220D(667699),         -- Quidway AR2220D FRAME
					 fnameAR2204(667700),         -- Quidway AR2204 FRAME
					 fnameUSR206(667701),         -- Quidway USR20-6 FRAME
					 fnameUSR208(667702),         -- Quidway USR20-8 FRAME
					 fnameSRG303W(667703),         -- Quidway SRG303W FRAME
					 fnameSRG303VW(667704),         -- Quidway SRG303VW FRAME
					 fnameSRG2320D(667705),         -- Quidway SRG2320D FRAME
					 fnameSRG2304(667706),         -- Quidway SRG2304 FRAME
					 fnameSRG2330(667707),         -- Quidway SRG2330 FRAME
					 fnameSRG1320(667708),         -- Quidway SRG1320 FRAME
					 fnameSRG1320W(667709),         -- Quidway SRG1320W FRAME
					 fnameAR151GEVDO(667710),       -- Quidway AR151G-EVDO FRAME
					 fnameAR156I(667711),           -- Quidway AR156I FRAME
					 fnameAR156IW(667712),          -- Quidway AR156IW FRAME
					 fnameAR157I(667713),           -- Quidway AR157I FRAME
					 fnameAR157IW(667714),          -- Quidway AR157IW FRAME
					 fnameAR168F(667715),           -- Quidway AR168F FRAME
					 fnameAR168FW(667716),          -- Quidway AR168FW FRAME
					 fnameAR169F(667717),           -- Quidway AR169F FRAME
					 fnameAR169W(667718),           -- Quidway AR169W FRAME
					 fnameAR169FW(667719),          -- Quidway AR169FW FRAME
					 fnameAR169BF(667720),          -- Quidway AR169BF FRAME
					 fnameAR169BFW(667721),         -- Quidway AR169BFW FRAME
					 fnameAR1220F(667722),          -- Quidway AR1220F FRAME
					 fnameAR1220FW(667723),         -- Quidway AR1220FW FRAME
					 fnameAR151S(667724),           -- Quidway AR151-S FRAME
					 fnameAR151WPS(667725),         -- Quidway AR151W-P-S FRAME
					 fnameAR151GUS(667726),         -- Quidway AR151G-U-S FRAME
					 fnameAR1220LS(667727),         -- Quidway AR1220L-S FRAME
					 fnameAR220148FES(667728),      -- Quidway AR2201-48FE-S FRAME
					 fnameAR2204S(667729),          -- Quidway AR2204-S FRAME
					 fnameAR2240S(667730),          -- Quidway AR2240-S FRAME
					 fnameAR159(667731),            -- Quidway AR159 FRAME
					 fnameAR531GPH(667732),         -- Quidway AR531GP-H FRAME
					 fnameAR531GBPDH(667733),       -- Quidway AR531GBP-D-H FRAME
					 fnameAR5312CH(667734),         -- Quidway AR531-2C-H FRAME
					 fnameAR531F2CH(667735),        -- Quidway AR531-F2C-H FRAME
					 fnameAR2540H(667736),          -- Quidway AR2540-H FRAME
					 fnameAR3560H(667737),          -- Quidway AR3560-H FRAME
					 fnameNE16EX-8(667738),         -- Quidway NE16EX-8 FRAME
					 fnameAR121S(667739),           -- Quidway AR121-S FRAME
					 fnameAR161FS(667740),          -- Quidway AR161F-S FRAME
					 fnameAR156W(667741),           -- Quidway AR156W FRAME
					 fnameAR159FW(667742),          -- Quidway AR159FW FRAME
					 fnameAR161FGWL(667743),        -- Quidway AR161FGW-L FRAME
					 fnameAR161FGL(667744),         -- Quidway AR161FG-L FRAME
					 fnameNE16EX-6(667745),         -- Quidway NE16EX-6 FRAME
					 fnameSRG2320E(667746),         -- Quidway SRG2320E FRAME
					 fnameAR162F(667747),           -- Quidway AR162F FRAME
					 fnameAR169FVW(667748),         -- Quidway AR169FVW FRAME
					 fnameAR161FW-P-M5(667749),     -- Quidway AR161FW-P-M5 FRAME
					 fnameAR511GW-UAV2M5(667750),   -- Quidway AR511GW-UAV2M5 FRAME
					 fnameAR169GFVW-L(667751),      -- Quidway AR169GFVW-L FRAME
					 fnameAR531GBP-U-H(667752),     -- Quidway AR531GBP-U-H FRAME
					 fnameAR161FW(667753),          -- Quidway AR161FW FRAME
					 fnameAR1220F-S(667754),        -- Quidway AR1220F-S FRAME
					 fnameAR511GW-LAV2M3(667756),   -- Quidway AR511GW-LAV2M3 FRAME
					 fnameAR161A(667757),           -- Quidway AR161A FRAME
					 fnameAR169A(667758),           -- Quidway AR169A FRAME
					 fnameAR161AG-L(667759),        -- Quidway AR161AG-L FRAME
					 fnameAR169AGW-I(667760),       -- Quidway AR169AGW-I FRAME
					 fnameAR1220EVW(667761),        -- Quidway AR1220EVW FRAME
					 fnameAR2220E(667762),          -- Quidway AR2220E FRAME
					 fnameAR3670(667763),           -- Quidway AR3670 FRAME
					 fnameAR3650(667764),           -- Quidway AR3650 FRAME
					 fnameAR2630(667765),           -- Quidway AR2630 FRAME
					 fnameAR2204E(667766),          -- Quidway AR2204E FRAME
					 fnameAR2220E-L(667767),        -- Quidway AR2220E-L FRAME
					 fnameAR511GW-L-B3(667768),     -- Quidway AR511GW-L-B3 FRAME
					 fnameAR511GW-LM7(667769),      -- Quidway AR511GW-LM7 FRAME
					 fnameAR513W-V3M8(667770),      -- Quidway AR513W-V3M8 FRAME
					 fnameAR1220E-S(667771),        -- Quidway AR1220E-S FRAME
					 fnameAR3260-S(667772),         -- Quidway AR3260-S FRAME
					 fnameAR531G-U-D-H(667773),     -- Quidway AR531G-U-D-H FRAME
					 fnameAR531GPe-U-H(667774),     -- Quidway AR531GPe-U-H FRAME
					 fnameAR531GR-U-H(667775),      -- Quidway AR531GR-U-H FRAME
					 fnameAR550-8FE-D-H(667776),    -- Quidway AR550-8FE-D-H FRAME
					 fnameAR550-24FE-D-H(667777),   -- Quidway AR550-24FE-D-H FRAME
					 fnameAR502G(667778),           -- Quidway AR502G FRAME
					 fnameAR531GP-H(667779),        -- Quidway AR531GP-H FRAME
					 fnameAR531GB-U-D-H(667780),    -- Quidway AR531GB-U-D-H FRAME
					 fnameAR161(667781),            -- Quidway AR161 FRAME
					 fnameAR161G-LE(667782),        -- Quidway AR161G-LE FRAME
					 fnameAR161G-HSPA7(667783),     -- Quidway AR161G-HSPA+7 FRAME
					 fnameAR161GW-L(667784),        -- Quidway AR161GW-L FRAME
					 fnameAR169(667785),            -- Quidway AR169 FRAME
					 fnameAR169G-LE(667786),        -- Quidway AR169G-LE FRAME
					 fnameAR169G-HSPA7(667787),     -- Quidway AR169G-HSPA+7 FRAME
					 fnameAR121(667788),            -- Quidway AR121 FRAME
					 fnameAR129(667789),            -- Quidway AR129 FRAME
					 fnameAR503GW-LM6(667790),      -- Quidway AR503GW-LM6 FRAME
					 fnameAR169-P-M9(667791),       -- Quidway AR169-P-M9 FRAME
					 fnameAR1220E(667792),          -- Quidway AR1220E FRAME
					 fnameAR1220EV(667793),         -- Quidway AR1220EV FRAME
					 fnameAR161F(667794),           -- Quidway AR161F FRAME
					 fnameAR169FGW-L(667795),       -- Quidway AR169FGW-L FRAME
					 fnameAR161-S(667796),          -- Quidway AR161-S FRAME

-- NE20E-X6:
					fnameNE20EX6DC(675840),        --NE20E-X6 chassis
					fnameNE20EX6AC(675841),        --NE20E-X6 chassis
					fnameNE20E-X2-M8(675842),   --Quidway CX600-X2-M8 FRAME,ne20e,AC. compatitable with old panel, no "AC" in name
					fnameNE20E-X1-M4(675843),      -- Quidway CX600-X1-M4 FRAME, ne20e
					fnameNE20E-X2-M16(675844),     -- Quidway CX600-X2-M16 FRAME, ne20e
					fnameNE20E-X2-M8-DC(675845),   --Quidway CX600-X2-M8 FRAME,ne20e,DC
					 fnameNE20E-S2E(675846),		 --Quidway CX600-M2E FRAME,ne20e-S2	 80Gps
					 fnameNE20E-S2F(675847),		 --Quidway CX600-M2F FRAME,ne20e-S2	160Gps
-- vRGW:
					fnamevRGW(679939),         --vRGW chassis

-- CloudEngine: 0x000A8000~0x000A8fff(688128~692223)
					 fnameCE12804(688128),                -- CloudEngine CE12804 FRAME,CE-BAK04A,12804 Backplane-1*1
					 fnameCE12808(688129),                -- CloudEngine CE12808 FRAME,CE-BAK08A,12808 Backplane-1*1
					 fnameCE12812(688130),                -- CloudEngine CE12812 FRAME,CE-BAK12A,12812 Backplane-1*1
					 fnameCE585048T4S2QEI(688131),        -- CloudEngine CE5850-48T4S2Q-EI Switch(48-Port 1000BASE-T,4-Port 10GBASE-X,2-Port 40GBASE-SR4,AC 110/220V)
					 fnameCE685048S4QEI(688132),          -- CloudEngine CE6850-48S4Q-EI Switch (48-Port 10GBASE-X,4-Port 40GBASE-SR4,AC 110/220V)
					 fnameCE685048T4QEI(688133),          -- CloudEngine CE6850-48T4Q-EI Switch(48-port 10GBASE-T,4-port 40GBASE-SR4,AC 110/220V)
					 fnameCE581024T4SEI(688134),          -- CloudEngine CE5810-24T4S-EI Switch(24-Port GE RJ45,4-Port 10GE SFP+)
					 fnameCE581048T4SEI(688135),          -- CloudEngine CE5810-48T4S-EI Switch(48-Port GE RJ45,4-Port 10GE SFP+)
					 fnameCE12816(688136),                -- CloudEngine CE12816 FRAME,CE-BAK16A,12816 Backplane-1*1
					 fnameCE585048T4S2QHI(688137),        -- CloudEngine CE5850-48T4S2Q-HI Switch(48-Port GE RJ45,4-Port 10GE SFP+,2-Port 40GE QSFP+)
					 fnameCE785032QEI(688138),            -- CloudEngine CE7850-32Q-EI Switch(32-Port 40GE QSFP+)
					 fnameCE681048S4QEI(688139),          -- CloudEngine CE6810-48S4Q-EI Switch (48-Port 10GE SFP+,4-Port 40GE QSFP+)
					 fnameCE681048S4QLI(688140),          -- CloudEngine CE6810-48S4Q-LI Switch (48-Port 10GE SFP+,4-Port 40GE QSFP+)
					 fnameCE681048SLI(688141),            -- CloudEngine CE6810-48S-LI Switch (48-Port 10GE SFP+)
					 fnameCE12804S(688142),               -- CloudEngine 12800S,CE01PBK04AS,CE12804S Power Backplane,1*1
					 fnameCE12808S(688143),               -- CloudEngine 12800S,CE01BAK08AS,CE12808S Backplane A,1*1
					 fnameCE685048S6QHI(688144),          -- CloudEngine CE6850-48S6Q-HI Switch (48-Port 10GE SFP+,6-Port 40GE QSFP+)

-- wlan:       0x000A9000~0x000A9fff(692224~696319)
					fnameES02acu(692224),               --Quidway S9300 ACU FRAME
					fnameAC6605-26-PWR(692225),          --Quidway AC6605-26-PWR Metro Service Platform
					fnameAC6005-8(692226),
					fnameACU2(692227),
					fnameAP6010SN(692228),
					fnameAP6010DN(692229),
					fnameAP6510DN(692231),
					fnameAP6610DN(692232),
					fnameAP5010DN(692233),
					fnameAP5010SN(692234),
					fnameAP7110DN(692235),
					fnameAP7110SN(692236),
					fnameAP3010DN(692237),
					fnameAP5030DN(692238),
					fnameAP5130DN(692239),
					fnameAC6005-8-PWR(692240),
					fnameAT815SN(692243),
					fnameAP8030DN(692245),
					fnameAP8130DN(692246),
					fnameAP9130DN(692247),

-- Frame Type for iODN products: range: 0x000B0000~0x000BFFFF  720,896~786,431
					 fnameMPU3101B-AC-1U(720898),              --MPU3101B-AC-1U
					 fnameMPU3101C-AC-1U(720899),              --MPU3101C-AC-1U
					 fnameMPU3101D-AC-1U(720900),              --MPU3101D-AC-1U
					 fnameMPU3101B-DC-1U(720901),              --MPU3101B-DC-1U
					 fnameMPU3101C-DC-1U(720902),              --MPU3101C-DC-1U
					 fnameMPU3101D-DC-1U(720903),              --MPU3101D-DC-1U
					 fnameAF11FPUA(721153),                    --AF11FPUA
					 fnameAF11FPUAT(721154),                   --AF11FPUAT
					 fnameGPX147-iMODF-6U(721155),             --GPX147-iMODF-6U
					 fnameAF11FATA(721156),                    --AF11FATA
					 fnameAF11FATC(721409),                    --AF11FATC
					 fnameAF11FATB(721410),                    --AF11FATB

					 fnameGPX147-iODF3101(729089),             --GPX147-iODF3101
					 fnameGXF147-iFDT3101(729090),             --GXF147-iFDT3101
					 fnameGXF147-iFDT3101D(729091),            --GXF147-iFDT3101D
					 fnameGXF147-FDT2107D(729092),             --GXF147-FDT2107D
					 fnameGPX147-iFAT3101(729093),             --GPX147-iFAT3101
					 fnameGPX147-iFAT3102-12(729094),          --GPX147-iFAT3102-12
					 fnameGPX147-iFAT3102(729095),             --GPX147-iFAT3102
					 fnameGPX147-ODF5101-CH2-1200mm(729096),   --GPX147-ODF5101-CH2-1200mm
					 fnameGPX147-ODF5101-FH2-1200mm(729097),   --GPX147-ODF5101-FH2-1200mm
					 fnameGPX147-ODF5101-CH2-900mm(729098),    --GPX147-ODF5101-CH2-900mm
					 fnameGPX147-ODF5101-FH2-900mm(729099),    --GPX147-ODF5101-FH2-900mm
					 fnameGPX147-ODF5101-CH9(729100),          --GPX147-ODF5101-CH9
					 fnameGPX147-ODF5101-FH9(729101),          --GPX147-ODF5101-FH9
					 fnameGXF147-iFDT3101D-A(729102),          --GXF147-iFDT3101D-A
					 fnameGXF147-iFDT3103D-432(729104),        --GXF147-iFDT3103D-432
					 fnameGPX147-iFAT3103T-16(729345),         --GPX147-iFAT3103T-16
					 fnameGPX147-iFAT3103T-24(729346),         --GPX147-iFAT3103T-24
					 fnameGPX147-iFAT3105T-32(729347),         --GPX147-iFAT3105T-32
					 fnameGPX147-iFAT3105T-36(729348),         --GPX147-iFAT3105T-36
					 fnameGPX147-iFAT3101TD-32(729349),        --GPX147-iFAT3101TD-32
					 fnameGPX147-iFAT3101TD-36(729350),        --GPX147-iFAT3101TD-36
					 fnameGPX147-iFAT3103TD-96-F(729351),      --GPX147-iFAT3103TD-96-F
					 fnameGPX147-iFAT3103TD-96-P(729352),      --GPX147-iFAT3103TD-96-P

					 fnameGPX147-SR5101-5U(737281),            --GPX147-SR5101-5U
					 fnameGPX147-SR5101-5U-2(737282),          --GPX147-SR5101-5U-2
					 fnameGPX147-SR5102-5U(737283),            --GPX147-SR5102-5U
					 fnameGXF147-FAT5201T(737284),             --GXF147-FAT5201T
 --hwRPS
					 fnameCPF318(786432),               --The RPS's Power Frame backplane.
					 fnameCFS01(786433),                --The RPS's Fan Frame.
					 fnameCPF104(786434),               --The RPS's with BT-C Power Frame backplane.
					 fnameCFS02(786435),                --The RPS's with BT-C Fan Frame.
					 fnameETP4830-A1(786436),           --The RPS's with AC-DC System Frame.
					 fnameETP4890-A2(786437),           --The RPS's with AC-DC System Frame.
					 fnameETP48150-A3(786438),          --The RPS's with AC-DC System Frame.
					 fnameCPF1042(786439),               --The RPS's with RTF-V Power Frame backplane.


-- Frame Type for hs security products:   range: 0x00ff1000~0x00ff1fff  16715776~16719871
					 fnameSU1Z21UHA(16715776),                   -- USG2200,SU1Z21UHA,USG2210 Host
					 fnameSU1Z21UHB(16715777),                   -- USG2200,SU1Z21UHB,USG2220 Host
					 fnameSU1Z21UHC(16715778),                   -- USG2200,SU1Z21UHC,USG2230 Host
					 fnameSU1Z21UHD(16715779),                   -- USG2200,SU1Z21UHD,USG2250 Host
					 fnameSU1Z22UHA(16715780),                   -- USG2200,SU1Z22UHA,USG2210 Host,HuaweiSymantec Overseas
					 fnameSU1Z22UHB(16715781),                   -- USG2200,SU1Z22UHB,USG2220 Host,HuaweiSymantec Overseas
					 fnameSU1Z22UHC(16715782),                   -- USG2200,SU1Z22UHC,USG2230 Host,HuaweiSymantec Overseas
					 fnameSU1Z22UHD(16715783),                   -- USG2200,SU1Z22UHD,USG2250 Host,HuaweiSymantec Overseas
					 fnameFWGZ21UHA(16715784),                   -- Quidway Eudemon,FWGZ21UHA,E200E-C Host
					 fnameFWGZ21UHD(16715785),                   -- Quidway Eudemon,FWGZ21UHD,E200E-F Host
					 fnameSRGZ2020(16715786),                    -- SRG20 Secure Routing Gateway,SRGZ2020,SRG20-20 AC Host
					 fnameSRGZ2021(16715787),                    -- SRG20 Secure Routing Gateway,SRGZ2021,SRG20-21 AC Host
					 fnameSRGZ2030(16715788),                    -- SRG20 Secure Routing Gateway,SRGZ2030,SRG20-30 AC Host
					 fnameSRGZ2031(16715789),                    -- SRG20 Secure Routing Gateway,SRGZ2031,SRG20-31 AC Host
					 fnameSRGZ2020IE(16715790),                      -- SRG20 Secure Routing Gateway,SRGZ2020IE,SRG20-20 AC Host
					 fnameSRGZ2021IE(16715791),                      -- SRG20 Secure Routing Gateway,SRGZ2021IE,SRG20-21 AC Host
					 fnameSRGZ2030IE(16715792),                      -- SRG20 Secure Routing Gateway,SRGZ2030IE,SRG20-30 AC Host
					 fnameSRGZ2031IE(16715793),                      -- SRG20 Secure Routing Gateway,SRGZ2031IE,SRG20-31 AC Host
					 fnameSU0Z11UHB(16715794),                       -- USG2100-SU0Z11UHB-USG2130 Host,HuaweiSymantec Overseas
					 fnameSU0Z13UHB(16715795),                       -- USG2100-SU0Z13UHB-USG2160 Host,HuaweiSymantec Overseas
					 fnameSRGZ23UHT(16715796),                       -- SRG3260,SRGZ23UHT,SRG3260 Host,with HS General Security Platform Software
					 fnameSU2Z12UAH(16715797),                       -- USG5100,SU2Z12UAH,USG5120 AC Host,with HS General Security Platform Software
					 fnameSU2Z12UDH(16715798),                       -- USG5100,SU2Z12UDH,USG5120 DC Host,with HS General Security Platform Software
					 fnameSU2Z13UHT(16715799),                       -- USG5100,SU2Z13UHT,USG5150 Host,with HS General Security Platform Software
					 fnameSU2Z22UAH(16715800),                       -- USG5100,SU2Z22UAH,USG5120BSR AC Host,with HS General Security Platform Software
					 fnameSU2Z22UDH(16715801),                       -- USG5100,SU2Z22UDH,USG5120BSR DC Host,with HS General Security Platform Software
					 fnameSU2Z23UHT(16715802),                       -- USG5100,SU2Z23UHT,USG5150BSR Host,with HS General Security Platform Software
					 fnameSRGZ12UAH(16715803),                       -- SRG3230,SRGZ12UAH,SRG3230 AC Host,with HS General Security Platform Software
					 fnameSRGZ22UAH(16715804),                       -- SRG3240,SRGZ22UAH,SRG3240 AC Host,with HS General Security Platform Software
					 fnameSRGZ22UDH(16715805),                       -- SRG3240,SRGZ22UDH,SRG3240 DC Host,with HS General Security Platform Software
					 fnameSRGZ13UHT(16715806),                       -- SRG3250,SRGZ13UHT,SRG3250 Host,with HS General Security Platform Software
					 fnameSU1ZAH10FE(16715807),			-- USG2200,SU1ZAH10FE,USG2210 AC Basic Configuration,(2GE,10FE,with 2*5FE MIC),with HS General Security Platform Software
					 fnameSU2Z42UAH(16715808),			-- USG5100,SU2Z42UAH,USG5120BSR AC Host,with HS General Security Platform Software
					 fnameSU2Z43UHTO1(16715809),			-- USG5100,SU2Z43UHT,USG5150BSR Host,with HS General Security Platform Software  Label duplicated with fnameSU2Z43UHT(16715811) and add 'O1'
		fnameSU2Z43UHTO2(16715810),			-- USG5500 1U Frame Unit  Label duplicated with fnameSU2Z43UHT(16715811) and add 'O2'
		fnameSU2Z43UHT(16715811),			-- USG5500 3U Frame Unit
		fnameSUAB13UAC(16715812),	            -- USG6600 SUAB13UAC  Frame Unit
		fnameNGFW1UL2(16715813),                    -- USG3600 L2 Frame Unit
		fnameNGFW1UL1(16715814),                    -- USG3600 L1 Frame Unit
		fnameNGFWSSM(16715815),                     -- NGFW SSM Frame Unit
-- Virtuil Frame of Net Management: from 0X70000000
					 fnameRF32(1879048192),                     --Virtuil Remote Frame,32 Slots
					 fnameRF64(1879048193)                      --Virtuil Remote Frame,64 Slots
					 }


		  HWPCBType ::= TEXTUAL-CONVENTION
				STATUS current
				DESCRIPTION
					 "This data type is used as the syntax of the
					 hwSlotType object in the definition of
					 HUAWEI-DEVICE-MIBs hwSlotTable.

					 The definition of this textual convention with the
					 addition of newly assigned values is published
					 periodically by the Huawei MIB Criterion Group, every
					 value indicate a PCB produced by Huawei.

					 "
				SYNTAX INTEGER
					 {
-- MD 5500
					 bnameUnknown(1),
					 bnameH511Mmxa(2),               -- MMXA board, mainboard of MA5100V1
					 bnameH511Mmxb(3),               -- MMXB board, mainboard of MA5100V1 with APON sub-board
					 bnameH511Mmxc(4),               -- MMXC board, mainboard of MA5100V2 with V5 characteritics etc.
					 bnameH511Asxa(5),               -- ASXA board, mainboard of MD5500, with ASX chip on board for 8x622M switch
					 bnameH511Aica(6),               -- ATM Interface Card, service board of MD5500, support STM-1 and STM-4
					 bnameH511Lanc(7),               -- 8 Port FE service board of MD/MA,
																-- for ethernet service access, support 64 VLAN
					 bnameH512Lanc(8),               -- Update version of H511LANC, support 32/2K VLAN, and region VLAN (IPDSLAM)
					 bnameH512Land(9),               -- Update version of H512LANC, support 32/256/2K VLAN (IPDSLAM),
																-- and 8FE/4FE/8Optic/4Optic/1GE subboard
					 bnameH511Adlb(10),
					 bnameH511Adlc(11),              -- 16 Port ADSL board
					 bnameH511Adld(12),              -- 32 Port ADSL board
					 bnameH512Adld(13),              -- 32 Port ADSL board, use another chipset contrast to H511ADLD
					 bnameH511Cesc(14),              -- 16 E1 Port CES board, not support TDM, with 2 E1 subboard
					 bnameH511Cesd(15),              -- 8 V35 Port CES board, with 3 V35 subboard
					 bnameH511Cese(16),              -- 8 E1 Port CES board, not support TDM, with 1 E1 subboard
					 bnameH511Cesf(17),              -- No subboard, for TDM use
					 bnameH511Cesh(18),              -- 16 E1 port CES board, with 2 E1 subboard, support TDM
					 bnameH512Cesh(19),              -- Same as H511CESH, diffrent from chipset
					 bnameH511Ea16(20),              -- Same as H511CESC, diffrent from chipset
					 bnameH511Ce8(21),               -- Same as H511CESE, diffrent from chipset
					 bnameH511Ce8V(22),              -- Same as H511CESD, diffrent from chipset
					 bnameH511Dt16(23),              -- 16 E1 Port CES board, only support TDM mode
					 bnameH511Dn16(24),              -- 16 E1 Port CES board, only support TDM mode, support DDN clock
					 bnameH511Frca(25),              -- 8 E1 Port FR board
					 bnameH511Frcb(26),              -- 8 V35 Port FR board
					 bnameH511Slfa(27),              -- 8 G.SHDSL port FR board, work in E1 mode
					 bnameH511Slfb(28),              -- 8 G.SHDSL port FR board, work in V35 mode
					 bnameH511Slca(29),              -- 8 G.SHDSL port CES board, work in E1 mode, not support TDM
					 bnameH511Slcb(30),              -- 8 G.SHDSL port CES board, work in V35 mode
					 bnameH511Splb(31),              -- 16 port split board word with H511ADLC
					 bnameH511Splc(32),              -- 32 port split board word with H511ADLD/H512ADLD
					 bnameH511Pots(33),              -- 32 Port Pots board
					 bnameH511Aiua(34),              -- ATM Interface Unit, can work with STM-1/IMA/E3 subboard, use the same PCB as MMXA
					 bnameH511Aiub(35),              -- ATM Interface Unit, can work with STM-1/IMA/E3/APON/STM-4 subboard, use the same PCB as MMXA
					 bnameH511Aiuc(36),              -- ATM Interface Unit, can work with STM-1/IMA/E3/APON/STM-4 subboard, use the same PCB as MMXC
					 bnameH511Ipuo(37),              -- Optic interface IP process board
					 bnameH511Epue(38),              -- Electric Interface IP process board
					 bnameH511Ipue(39),              -- Electric interface ehternet process board
					 bnameH511Epuo(40),              -- Optic interface ehternet process board
					 bnameH511Vspd(41),              -- VoDSL process board
					 bnameH511Msua(42),              -- 2 Port STM-1(with 2M structure) access board
					 bnameH511Imua(43),              -- 32 port IMA interface access board
					 bnameH511Smxa(44),              -- main board in slave frame for DSLAM use, use the same PCB as MMXA
					 bnameH511Smxb(45),              -- main board in slave frame for DSLAM use, use the same PCB as MMXB
					 bnameH511Sepa(46),              -- Board used to connect slave frame for DSLAM use
					 bnameEsc(47),                   -- For HONET
					 bnameRsp(48),                   -- For HONET
					 bnamePv8(49),                   -- For HONET
					 bnameApru(50),                  -- For HONET
					 bnameAprx(51),                  -- For HONET
					 bnameAsl(52),                   -- For HONET
					 bnameA32(53),                   -- For HONET
					 bnameDsl(54),                   -- For HONET
					 bnameMlc(55),                   -- For HONET
					 bnameIdla(56),                  -- For HONET
					 bnameCdi(57),                   -- For HONET
					 bnameAti(58),                   -- For HONET
					 bnameTss(59),                   -- For HONET
					 bnamePwx3(60),                 -- For HONET
					 bnamePwxA(61),                 -- For HONET
					 bnameEmu(62),                   -- For HONET
					 bnameHwc(63),                   -- For HONET
					 bnameVfb(64),                   -- For HONET
					 bnamePvu(65),                   -- For HONET

					 bnameH511Shla(66),              -- 32-port ATM G.SHDSL service board, a new service board for the masters Frame in 51V2
					 bnameH511Adle(67),              -- 32-port integrated service board of ADL and SPL, a new service board for the master Frame in 51V2
					 bnameMD5500H511BTSA(68),        -- H511BTSA (broadband and narrowband test board)
					 bnameh511Land(69),              -- H511lLAND board

					 bnameH601Apma(70),              -- New control board for the master Frame of the UA3000
					 bnameH601Apsa(71),              -- New control board for the slave Frame of the UA3000
					 bnameH601Apfa(72),              -- New control board for the master Frame of the UA3000, with the front-access line
					 bnameH601CSL(73),              -- New service board of the UA3000
					 bnameH601Cslf(74),              -- New service board of the UA3000, with the front-access line
					 bnameH601ADL(75),              -- New service board of the UA3000
					 bnameH512Adle(76),              -- 32-port integrated service board of ADL and SPL, a new service board for the master Frame in 51V2
					 bnameH512Adli(77),              -- 32-port ISDN ADL service board, a new service board for the master Frame in 51V2
					 bnameH531BASA(78),              -- New service board of the MA5300
					 bnameH531BASE(79),              -- New service board of the MA5300

-- MUSA
					 bnameSmb(80),                   -- Control board
					 bnameHrb(81),                   -- Uplink board
					 bnameHab(82),                   -- Uplink board

-- MA5200
					 bnameNat(83),
					 bnameCts(84),

					 bnameH511BTSB(85),              -- For MA5100&MD5300, Broad test card B , providing test for broad subscribers

-- AG
					 bnamePvm(90),

					 bnameSdl(100),                  -- SDL (Narrowband service board, which provides 4 E1 ports and 4 G.SHDSL ports)
					 bnameH511Msuc(101),             -- MSUC board, which supports 2 optical ports and 126[LU1] E1 ports
					 bnameH511AsxB(102),             -- Control board ASXB

-- Board types of A8010
					 bnamVspNas(110),                -- VSPNAS board, whose number is AS31VSPA03032106
					 bnamVspIpp(111),                -- VSP IPP board, whose number is HSPAS31VSPA03032106
					 bnamVspHsp(112),                -- VSP HSP board, whose number is AS31VSPA03032106
					 bnamVspAnyport(113),            -- VSP AnyPort board, whose number is AS31VSPA03032106
					 bnamVsu(114),                   -- The number of this board is AS31VSUA03033127 or AS31HSPA.
					 bnamHsp(115),                   -- The number of this board is AS31MSTU03032762.
					 bnamFrb(116),                   -- The number of this board is AS31FRBA03034101 or AS31FRBB03034102.
					 bnamMstu(117),                  -- The number of this board is AS31MSTU03032762.
-- ESR board type
					 bnameMpua(130) ,                -- BS21MPUA
					 bnameMpub(131) ,                -- BS22MPUB
					 bnameNeta(132) ,                -- BS21NETA
					 bnameNetb(133) ,                -- BS22NETB
					 bnameSFCA(134) ,                -- BS21NETA
					 bnameLpua(135) ,                -- BS21LPUA
					 bnameLpub(136) ,                -- BS22LPUB
					 bnameLpuc(137) ,                -- BS22LPUC
					 bnameLpud(138) ,                -- BS22LPUD
-- ESR boards that have same hardware but different software
					 bnameSpubBas(139) ,             -- SN01SPUB
					 bnameSpubSerm(140) ,            -- SN01SPUB
					 bnameLpui(141) ,                -- SN01LPUI
					 bnameLpuh(142) ,                -- SN01LPUH
					 bnameO2CC(143) ,                -- BS2202CC
-- MA5105
					 bnameMa5105e1(200),             -- E1
					 bnameMa5105fe(201),             -- FE
					 bnameMa5105adsl(202),           -- ADSL
					 bnameMa5105ima(203),            -- IMA
-- MD5500
					 bnameMD5500Hsl(204),            -- HSL (narrowband service board, which provides two E1 ports and two V35 ports)
					 bnameMD5500PV4(205),            -- PV4 (narrowband master node board, which provides four less E1 ports than PV8)
-- MA5300
					 bnameMa5300ESM(206),            -- Ethernet switching control board of the MA5300. Its BOM is 03033569.
					 bnameMa5300VDSL16(207),         -- 16-port Ethernet access VDSL service board of the MA5300. Its BOM is 03033632.
					 bnameMa5300VDSL24(208),         -- 24-port Ethernet access VDSL service board of the MA5300. Its BOM is 03035806.
					 bnameMa5300ADSL(209),           -- 48-port ADSL service board of the MA5300
-- UA5000
					  bnameH601Aiua(210),            -- ATM service board of the UA5000
-- MD5500
					 bnameH511IMUB(211),             -- 16-port IMA service board of the MD5500
					 bnameH511IMUD(212),             -- 32-port IMA service board of the MD5500
					 bnameH531EADL(213),             -- 24-port ADSL service board
					 bnameH531EVDB(214),             -- 24-port VDSL service board that supports the band plans of 10BASE-S and PLAN9998
					 bnameH533ESHA(215),             -- 24-port G.SHDSL board of the MA5300
					 bnameH531ETHA(216),             -- Ethernet access board of the MA5300. This board provides eight FE ports and one subslot.
					 bnameH533EADB(217),             -- 48-port ADSL2+ service board of the MA5300
-- S3026V
					 bnameH523VDLA(218),             -- Control board of the S3026V
					 bnameH523VDLAVDSA(219),         -- Control board + 8-port VDSA subboard of the S3026V
-- UA5000
					 bnameH601SDL(220),             -- 16-port G.SHDSL board of the UA5000
					 bnameH601DEHA(221),             -- UA5000's 16-port board that supports E1 transparent transmission
					 bnameH601VDL(222),             -- 16-port VDSL board of the UA5000
					 bnameH601IPMA(264),             -- UA5000's control board that forwards the service upstream to the IP network
					 bnameH602ADM(265),             -- 16-port ADSL2+ full-broadband board of the UA5000
-- MA5100
					 bnameH512ADLC(230),             -- 16-port ADSL service board
					 bnameH513ADLD(231),             -- 32-port ADSL service board
					 bnameH513ADLE(232),             -- 32-port ADSL board of the MA5100. This board provides a maximum downstream rate of 8 Mbit/s.
					 bnameH513ADLF(233),             -- 32-port ADSL board of the MA5100. This board provides a maximum downstream rate of 25 Mbit/s.
					 bnameH513ADLI(234),             -- 32-port ISDN ADL service board
					 bnameH514ADLD(235),             -- 32-port ADSL service board
					 bnameH515ADLD(236),             -- 32-port ADSL service board
					 bnameH516ADLD(237),             -- 32-port ADSL service board
					 bnameH517ADLD(238),             -- 32-port ADSL service board
					 bnameH518ADLD(239),             -- 32-port ADSL service board
					 bnameH519ADLD(240),             -- 32-port ADSL service board
					 bnameH514ADLE(241),             -- 32-port ADSL board of the MA5100. This board provides a maximum downstream rate of 8 Mbit/s.
					 bnameH515ADLE(242),             -- 32-port ADSL board of the MA5100. This board provides a maximum downstream rate of 8 Mbit/s
					 bnameH516ADLE(243),             -- 32-port ADSL board of the MA5100. This board provides a maximum downstream rate of 8 Mbit/s.
					 bnameH517ADLE(244),             -- 32-port ADSL board of the MA5100. This board provides a maximum downstream rate of 8 Mbit/s.
					 bnameH518ADLE(245),             -- 32-port ADSL board of the MA5100. This board provides a maximum downstream rate of 8 Mbit/s.
					 bnameH519ADLE(246),             -- 32-port ADSL board of the MA5100. This board provides a maximum downstream rate of 8 Mbit/s.
					 bnameH511Spli(247),             -- split board word with ADLI
					 bnameSepl(248),                 -- SEP subtend board
					 bnameSmxl(249),                 -- SEP subtend board
-- MA5105
					 bnameMa5105shdsl(250),          -- 16-port SHDSL board
					 bnameMa5105fc(251),             -- FE subtend board
-- MA5105 N2B
					 bnameN2Be1(252),                -- N2B board that provides the E1 port
					 bnameN2Bfe(253),                -- N2B board that provides the FE port
					 bnameN2Bima(254),               -- N2B board that provides the IMA port
					 bnameN2Badslb08(255),           -- N2B board that provides 8 ADSL ports
					 bnameN2Badslbsl(256),           -- N2B board that provides 16 ADSL ports
					 bnameN2Bshdslb08(257),          -- N2B board that provides 8 SHDSL ports
					 bnameN2Bshdslbsl(258),          -- N2B board that provides 16 SHDSL ports
-- MA5100
					 bnameADLC(259),                 -- 16-port ADSL service board (ADLC series)
					 bnameADLD(260),                 -- 32-port ADSL board (ADLD series)
					 bnameADLE(261),                 -- 32-port ADSL board (ADLE series) that provides a maximum downstream rate of 8 Mbit/s
					 bnameADLI(262),                 -- 32-port ISDN ADL service board (ADLI series)
					 bnameADL(263),                  -- H512ADLF, H512ADLGADL and later ADL boards
					 -- bnameH601IPMA(264),              UA5000's control board that forwards the service upstream to the IP network
					 -- bnameH602ADMB(265),              UA5000 ADSL2+ board
					 bnameH511TSBA(266),             -- H511TSBA board for routing the passive test bus
					 bnameH511VDLA(267),             -- VDSL board of the MA5100
					 bnameVPU(268),                  -- VPU board of the MD
--S3026V
					 bnameH523VDLA2(269),

-- MA5105
					 bnameMa5105adli(270),           -- ADLI board, which provides 16 ports
					 bnameMa5105adlh(271),           -- ADLH board, which provides 16 ports
					 bnameMa5105adce(272),           -- 16-port ADSL2+ board
					 bnameMa5105adch(273),           -- 16-port ADSL2+ board
					 bnameMa5105adid(274),           -- 16-port ADSL2+ Over ISDN board
					 bnameH601ADLB(275),             -- 16-port ADSL board with a built-in splitter (TI AC5 chipset + 7350) (no relay)
					 bnameH601CSLB(276),             -- 16-port ADSL and POTS combo service board with a built-in splitter (TI AC5 chipset + 7350) (no relay)
					 bnameH601SDLB(277),             -- 16-port ATM G.SHDSL service board (GSV chipset + 7350/250 + high-rate connector + four-wire feature)
					 bnameH602ADMC(278),             -- 16-port ADSL/ADSL2+ service board with a built-in splitter (GSV chipset + 7350/250 + high-rate connector)(two relays)
--S3026V

					 bnameH523VDLAVDSA2(279),

-- UA5000
					 bnameH601AIUB(280),             -- UA IMA, E3, or ATM 155M upstream service board
					 bnameH601CSLI(281),             -- UA CSLI board, a 16-port ADSL full-broadband board
					 bnameH601VDLB(282),             -- UA VDLB board, a 16-port QAM VDSL board, which supports board N+1 backup
					 bnameH602ADMI(283),             -- UA ADMI board, a 16-port ADSL2+ board with a built-in BT splitter
					 bnameH601CSLC(284),             -- UA CSLC board, a 16-port ADSL broadband and narrowband combo board
					 bnameH523mfce(299),             -- H523MFCE
-- HONET board type, for iManager N2000 BMS HV20 integrate management
					 bnameHV20ASL(300),              -- For HONET, analog subscriber board of HONET SIPP II/III system,
																--having 16 paths of subscriber lines on each board.
					 bnameHV20DRV(301),              --For HONET, dual-tone number receiving board of HONET SIPP II/III.
																--Each board configures 16 dual-tone number receivers. Meanwhile,
																--DRV board also provides the function of level switch between
																--difference level and TTL level.
					 bnameHV20RSA(302),              -- For HONET, a main board, usually used in remote subscriber Frame.
					 bnameHV20DTM(303),              -- For HONET, digital trunk board of HONET SIPP II/III system.
																-- Each board provides 2 E1 interfaces.
					 bnameHV20DSL(304),              -- For HONET, digital subscriber board of HONET SIPP II/III system.
																-- Each board configures 8 paths of digital subscriber lines.
					 bnameHV20DDU(305),              -- For HONET, digital interface board of HONET SIPP II/III system.
																-- Each board performs the switch between 2 paths 64K bit/s signal and V35, V24 signals.
					 bnameHV20TSS(306),              -- For HONET, test board of HONET SIPP II/III system,
																-- providing test for analog subscribers and digital subscribers.
					 bnameHV20TSI(307),              -- For HONET, test board used in digital subscriber testing. This is no longer in use.
					 bnameHV20AV5(308),              -- For HONET, master control board of HONET SIPP II/III system,
																-- responsible f or the protocol processing, equipment management, and network exchanging.
					 bnameHV20PWC(309),              -- For HONET, power supply board of HONET SIPP II/III system.
																-- PWC board does not provide 48V generator,
																-- and is only used in the master control Frame of the SIPP II system.
					 bnameHV20PWX(310),              -- For HONET, power supply board of HONET SIPP II/III system.
																-- PWX board provides 48V generator, which is used in various shelves.
					 bnameHV20DM4(311),              -- For HONET, tributary interface board. Each board provides the 4 paths
																-- of switch between sub-synchronous PCM lines and 2112Kbit/s synchronous code,
																-- and 4 paths of inversion. It also determines the direction of receiving and
																-- sending of the 4 paths of signals, which realizes the function of self-healing switch.
					 bnameHV20TIU(312),              -- For HONET, optical interface board of OLT terminal station.
																-- The function of a TIU board is to multiplex the 28 paths of 2112 kbit/s tributary
																-- signals sent by 7 DM4, and then send them back to the 7 DM4.
					 bnameHV20NMI(313),              -- For HONET, used in OLT, ONU-512, ONU-128, ONU-1000A of the HONET system,
																-- functioning as maintenance of the optical transmission equipment,
																-- environment monitoring and equipment management.
					 bnameHV20FIU(314),              -- For HONET, optical interface in the trunk ONU,
																--providing simultaneously two pairs of optical interfaces.
					 bnameHV20EIU(315),              -- For HONET, used in the E1 interface of ONU-128.
																-- EIU card completes the justification and restoration of two 2M signals.
					 bnameHV20BIU(316),              -- For HONET, optical interface card used in triburary ONU,
																-- accepting 2 to 6 2M point to point transmission.
					 bnameHV20ILM(317),              -- For HONET, InfoLink management card of CATV subscriber shelf.
					 bnameHV20ESC(318),              -- For HONET, environment monitor interface board of HONET SIPP II/III system,
																-- providing the environment quantity of the remote ONU and monitoring the operation of the power supply.
					 bnameHV20PWH(319),              -- For HONET, power supply board of PHD optical transmission system, used in various transmission shelves.
					 bnameHV20ILR(320),              -- For HONET, InfoLink optical receiving board of CATV subscriber Frame.
					 bnameHV20ILT(321),              -- For HONET, InfoLink optical sending board of CATV subscriber Frame.
					 bnameHV20PV8(322),              -- For HONET, the master control board of HONET SIPP II/III system, responsible for protocol handling,
																-- equipment management, and network switch. The only difference between PV8 board and PV4 board is that
																-- the former has 8 paths of standard E1 interfaces while the latter has only 4.
					 bnameHV20PV4(323),              -- For HONET, the master control board of HONET SIPP II/III system, responsible for protocol handling,
																-- equipment management, and network switch. The only difference between PV8 board and PV4 board is that
																-- the former has 8 paths of standard E1 interfaces while the latter has only 4.
					 bnameHV20RSP(324),              -- For HONET, a new-type remote RSA board of HONET SIPP II/III system whose convergence rate can be adjusted,
																-- connecting to remote ONU subscribers collaboratively with digital trunk cards.
																-- Each RSP board may configure at most 4 2M PCM links, and can realize 1:1, 1:2, and 1:4 convergence rates.
					 bnameHV20HSL(325),              -- For HONET, N*64 super rate board (N=1~31), of HONET SIPP II/III system.
																--Each board provides externally 2 synchronous V.35 interface in the mode of DCE or DTE, and two FE1 interfaces.
					 bnameHV20ATI(326),              -- For HONET, analog trunk interface board of HONET SIPP II/III system,
																-- used to connect subscriber machines which have only EM interfaces,
																-- realizing EM communication transfer in the access network. Each AIT cards provides 6 physical EM ports.
																--The slots are compatible with such board slots as ASL, DSL, and VFB.
					 bnameHV20SRX(327),              -- For HONET, sub-rate board of HONET SIPP II/III system.
																-- Each board provides externally 5 synchronous/asynchronous compatible V.24 interfaces in DCE mode,
																-- completing the multiplexing of multiple sub-rate data specified in X.50 and X.58 protocols.
					 bnameHV20VFB(328),              -- For HONET, 2 line/4 line voice frequency interface board of HONET SIPP II/III system,
																-- providing the private network of the railway dispatching system with private interface board.
					 bnameHV20VDM(329),              -- For HONET, a board to stack sound frequencies in HONET SIPP II/III system.
																-- It is inserted in the subscriber Frame, and is compatible with other board slots in such cards as ASL,
																-- DSL, and VFB. Each VDM board has 16 channels, supporting at most 16 paths of voice frequency tiling.
					 bnameHV20CDI(330),              -- For HONET, analog trunk board in HONET SIPP II/III system, supporting DDI service.
																-- CDI board may dynamically distribute time slots, and its slots are compatible with the slots of
																-- such cards as ASL, DSL, and VFB.
					 bnameHV20ASP(331),              -- For HONET, AV5 board of the remote main node of HONET SIPP II/III system (HV20A003 version or above not supportable),.
					 bnameHV20DTE(332),              -- For HONET, a new- type 2M bit/s digital trunk interface board of HONET SIPP II/III system.
																-- Each board configures 8 2M PCM 30/32 systems.
					 bnameHV20WSA(333),              -- For HONET, remote main node board which is wireless connected to ETS450 WLL base station in
																-- HONET SIPP II/III system. Each board outputs 2M E1 trunk, mainly used in WSA subscriber Frame.
																-- WSA board communicates with the host via RSA protocol, which equals to RSA main node board.
					 bnameHV20DTH(334),              -- For HONET, 1.544M bit/s digital leased line interface board of HONET SIPP II/III system.
																-- Each board configures 8 1.544M PCM 22/24 systems, providing T1 leased line service.
					 bnameHV20ASL32(335),            -- For HONET, a new-type analog subscriber board of HONET SIPP II/III system,
																-- which can provide 32 paths of subscriber lines on each board.
					 bnameHV20NPU(336),              -- For HONET, net process unit in HONET SIPP II/III system, which can provide 10M Ethernet interface .
					 bnameHV20DLI(337),              -- For HONET, DECT interface board, which provide 32 channel for wireless subscriber.
					 bnameHV20CKS(338),              -- For HONET, a clock board of HONET SIPP II/III system.
					 bnameHV20CKD(339),              -- For HONET, a clock board of HONET SIPP II/III system.
					 bnameHV20SBL(340),              -- For HONET, 2B1Q board of HONET SIPP II/III system. Each board provides 8 paths of 2B1Q interfaces,
																-- which are used in DDN access.
					 bnameHV20MLC(341),              -- For HONET, a new-type SBL board, can be used as both subscriber board and main node board.
					 bnameHV20SCS(342),              -- For HONET, SCS board is subrate concentrate switch board that is used with SRX board, MTA port,
																-- DE1 Channel, and this board only support connection between subrate of 2.4K, 4.8K, 9.6K, 19.2K.
					 bnameHV20HWC(343),              -- For HONET, a signal level convert board, only used for PV8 board in PV8-10 control Frame.
-- MIM & SIC card for router:
					 bnameReserverd(400),            -- For router, Reserved board name
					 bnameUnknownboard(401),              -- For router, Unknown board
					 bnameMIM8AS(402),              -- For router, MIM card with 8 asynchronous serial port
					 bnameMIM4SA(403),              -- For router, MIM card with 4 high-speed synchronous/asynchronous serial port
					 bnameMIM4BS(404),              -- For router, MIM card with 4 ISDN BRI S/T port
					 bnameMIM2E1(405),              -- For router, MIM card with 2 channelized cE1/PRI port
					 bnameMIM4E1(406),              -- For router, MIM card with 4 channelized cE1/PRI port
					 bnameMIM1FE(407),              -- For router, MIM card with 1 10Base-T/100Base-TX port
					 bnameMIM1E1(408),              -- For router, MIM card with 1 channelized cE1/PRI port
					 bnameMIM2FE(409),              -- For router, MIM card with 2 10Base-T/100Base-TX port
					 bnameMIM2VI(411),              -- For router, MIM card with 2 line voice processing unit
					 bnameMIM4VI(412),              -- For router, MIM card with 4 line voice processing unit
					 bnameMIM30VI(413),             -- For router, MIM card with 30 line voice processing unit
					 bnameMIM2S1B(414),             -- For router, MIM card with 2 synchronous/asynchronous serial port and 1 ISDN BRI S/T port
					 bnameMIM2SA(415),              -- For router, MIM card with 2 high-speed synchronous/asynchronous serial port
					 bnameMIM16AS(416),             -- For router, MIM card with 16 asynchronous serial port
					 bnameMIMnew8AS(417),           -- For router, MIM card with 8 asynchronous serial port (new)
					 bnameMIM8LSA(418),             -- For router, MIM card with 8 low-speed synchronous/asynchronous serial port
					 bnameMIM2FXS(419),             -- For router, MIM card with 2 FXS port
					 bnameMIM2FX0(420),             -- For router, MIM card with 2 FXO port
					 bnameMIM2EM(421),              -- For router, MIM card with 2 E&M port
					 bnameMIM4FXS(422),             -- For router, MIM card with 4 FXS port
					 bnameMIM4FXO(423),             -- For router, MIM card with 4 FXO port
					 bnameMIM4EM(424),              -- For router, MIM card with 4 E&M port
					 bnameFixedSA(425),             -- For router 2620/2621, 1/2 fixed high-speed synchronous serial port
					 bnameMIME1VI(426),             -- For router, MIM card with 1 E1 port for voice processing
					 bnameMIM12AM(427),             -- For router, MIM card with 12 analog modem port
					 bnameMIM6AM(428),              -- For router, MIM card with 6 analog modem port
					 bnameMIMNDEC(429),             -- For router, MIM card for network encryption
					 bnameMIMnew2SA(430),           -- For router, MIM card with 2 high-speed synchronous/asynchronous serial port (new)
					 bnameFixedAux(431),            -- For router, Fixed Aux port
					 bnameFixedConsole(432),        -- For router, Fixed Console Port
					 bnameFixedSA1760(433),        -- For router 1760/2610/2611, fixed synchronous/asynchronous serial port
					 bnameSIC1FE(434),              -- For router, SIC card with 1 10Base-T/100Base-TX port
					 bnameSIC1SA(435),              -- For router, SIC card with 1 high-speed sychronous/asynchronous serial port
					 bnameSIC3AS(436),              -- For router, SIC card with 3 asynchronous serial port
					 bnameSIC1E1(437),              -- For router, SIC card with 1 channelized cE1/PRI port
					 bnameSIC1T1(438),              -- For router, SIC card with 1 channelized cT1/PRI port
					 bnameSIC1BU(439),              -- For router, SIC card with 1 ISDN BRI U port
					 bnameSIC2BU(440),              -- For router, SIC card with 2 ISDN BRI U port
					 bnameSIC1BS(441),              -- For router, SIC card with 1 ISDN BRI S/T port
					 bnameSIC2BS(442),              -- For router, SIC card with 2 ISDN BRI S/T port
					 bnameSIC1AM(443),              -- For router, SIC card with 1 analog modem port
					 bnameSIC2AM(444),              -- For router, SIC card with 2 analog modem port
					 bnameSIC1EM(445),              -- For router, SIC card with 1 E&M port
					 bnameSIC2EM(446),              -- For router, SIC card with 2 E&M port
					 bnameSIC1FXS(447),             -- For router, SIC card with 1 FXS port
					 bnameSIC2FXS(448),             -- For router, SIC card with 2 FXS port
					 bnameSIC1FXO(449),             -- For router, SIC card with 1 FXO port
					 bnameSIC2FXO(450),             -- For router, SIC card with 2 FXO port
					 bnameMIM6FCM(451),             -- For router, MIM card with 6 fast connect modem port
					 bnameMIM8SA(452),              -- For router, MIM card with 8 high-speed sychronous/asychronous serial port
					 bnameMIM1T1(453),              -- For router, MIM card with 1 channelized cT1/PRI port
					 bnameMIM2T1(454),              -- For router, MIM card with 2 channelized cT1/PRI port
					 bnameMIM4T1(455),              -- For router, MIM card with 4 channelized cT1/PRI port
					 bnameMIMT1VI(456),             -- For router, MIM card with 1 T1 port for voice processing
					 bnameMIM4FCM(457),             -- For router, MIM card with 4 fast connect modem port
					 bnameMIM2FCM(458),             -- For router, MIM card with 2 fast connect modem port
					 bnameMIMcE3(459),              -- For router, MIM card with 1 channelized E3 port
					 bnameMIM6AME(460),             -- For router, MIM card with 6 analog modem port (new)
					 bnameMIM12AME(461),            -- For router, MIM card with 12 analog modem port (new)
					 bnameMIM1E1F(465),            -- For router, MIM card with 1 fractional E1 port
					 bnameMIM2E1F(466),            -- For router, MIM card with 2 fractional E1 port
					 bnameMIM4E1F(467),            -- For router, MIM card with 4 fractional E1 port
					 bnameMIM1T1F(468),            -- For router, MIM card with 1 fractional T1 port
					 bnameMIM2T1F(469),            -- For router, MIM card with 2 fractional T1 port
					 bnameMIM4T1F(470),            -- For router, MIM card with 4 fractional T1 port
					 bnameSIC1E1F(471),            -- For router, SIC card with 1 fractional E1 port
					 bnameSIC1T1F(472),            -- For router, SIC card with 1 fractional T1 port
					 bnameMIMcT3(473),              -- For router, MIM card with 1 channelized T3 port
					 bnameMIMATMADSL1(474),        -- For router, MIM card with 1 adsl port
					 bnameMIMATMADSL2(475),        -- For router, MIM card with 2 adsl ports
					 bnameMIMATM155(476),          -- For router, MIM card with 1 155M port
					 bnameMIM8AS701(477),          -- For router, MIM card with 8 asynchronous serial port(using SD701)
					 bnameMIM16AS701(478),         -- For router, MIM card with 16 asynchronous serial port(using SD701)
					 bnameMIM4SA701(479),          -- For router, MIM card with 4 high-speed synchronous/asynchronous serial port(using SD701)
					 bnameMIM2SA701(480),          -- For router, MIM card with 2 high-speed synchronous/asynchronous serial port(using SD701)
-- 8070:
					 bnameRTC1RSU(550),              -- RSU process board
					 bnameRTC1RSK(551),              -- RSU back board
					 bnameRTC2RSUA(552),             -- RSU process board 128M
					 bnameRTC2RSUB(553),             -- RSU process board 256M
					 bnameRTC2RSUC(554),             -- RSU process board 512M
					 bnameRTC2RSEU(555),             -- RSU back board
					 bnameRTC1VIU(556),              -- VIU process board
					 bnameRTC1BAK(557),              -- VIU back board
					 bnameRTC2VIUA(558),             -- VIU process board 128M
					 bnameRTC2VIUB(559),             -- VIU process board 256M
					 bnameRTC2VIUC(560),             -- VIU process board 512M
					 bnameRTC2VIEU(561),             -- VIU back board version 2
					 bnameRTC4VIU(562),              -- Enhanced VIU process board
					 bnameRTC1HAU(563),              -- HAU
					 bnameRTC2HAU(564),              -- HAU version 2
					 bnameRTC1SMMU(565),             -- ALU used by NE08
					 bnameRTC2ALU(566),              -- ALU used by NE16E, NE08E and NE05
					 bnameRTC4VIUA(567),             -- NE05/08/16E front board
					 bnameRTC4VIUB(568),             -- NE05/08/16E front board
					 bnameRTC4VIUC(569),             -- NE05/08/16E front board
					 bnameRTC1RSHC(570),             -- NE05/08/16E board:for ne05 rshc
					 bname5FEMP(571),                -- NE05/08/16E board:for imu
					 bname2GOMP(572),                -- NE05/08/16E board:for imu
					 bname1GOMP(573),                -- NE05/08/16E board:for imu
					 bname2GEMP(574),                -- NE05/08/16E board:for imu
					 bname1GEMP(575),                -- NE05/08/16E board:for imu
					 bname5FEMK(576),                -- NE05/08/16E board:for imu
					 bname3FEMK(577),                -- NE05/08/16E board:for imu
					 bname2GOMK(578),                -- NE05/08/16E board:for imu
					 bname2GEMK(579),                -- NE05/08/16E board:for imu
					 bname1GOMK(580),                -- NE05/08/16E board:for imu
					 bname1GEMK(581),                -- NE05/08/16E board:for imu
					 bnameRTC3RSUB(582),             -- RSU process board 256M version 3
					 bnameRTC3RSUC(583),             -- RSU process board 512M version 3
					 bnameRTC2VIUS(584),             -- VIU process board 256M,used only by NE05
					 bnameRTC3VIUB(585),             -- VIU process board 256M version 3
					 bnameRTC8VIUB(586),             -- VIU process board 256M version 8
					 bnamePWR(587),                  -- Power supply
					 bnameFAN(588),                  -- Fan
					 bname3FEMP(589),                -- NE05/08/16E board:for imu front
					 bnameRTC2RSUD(590),             -- RSU process board 1G

-- 8011:
					 bnameCR01BAKB(600),             -- For NE80, backplane of NE80
					 bnameCR01BAKC(601),             -- For NE40-8, backplane of NE40-8
					 bnameCR01BAKD(602),             -- For NE40-4, backplane of NE40-4
					 bnameCR01BAKE(603),             -- For NE40-2, backplane of NE40-2
					 bnameCR01PWRB(604),             -- For NE80, power supply card of NE80
					 bnameCR01DPRB(605),             -- For NE80, power destribution card of NE80
					 bnameCR01PWRD(606),             -- For NE40, power supply card of NE40
					 bnameCR01FANB(607),             -- For NE80, fan card of NE80
					 bnameCR01FAND(608),             -- For NE40, fan card of NE40
					 bnameCR01MPUB(609),             -- For NE80, main control card of NE80
					 bnameCR01SRUB(610),             -- For NE40, main control card of NE40
					 bnameCR01NETB(611),             -- For NE80, switch card of NE80
					 bnameCR01CLKB(612),             -- For NE80, clock card of NE80
					 bnameCR01HUBB(613),             -- For NE80, HUB card of NE80
					 bnameCR01LPUB(614),             -- For NE80 & NE40, mother card of NE80 and NE40
					 bnameCR01NATB(615),             -- For NE80 & NE40, NAT card of NE80 and NE40

-- MA5300:
					 bnameH531ESME(616),             -- Ethernet switching control board. This board differs from the ESMA board in the
																-- following way: Subslot 2 of this board supports only electric port FE subboard.
					 bnameH531EIUA(617),             -- Upstream service board, which supports a GE subboard
-- MA5100 ADSL boards
					 bnameH511Mmxs(620),             -- H511MMXS control board of the MA5100. This board does not provide the clock subboard and the service subboard.
					 bnameADLF(622),                 -- 32 port ADSL board over pots
					 bnameADLG(623),                 -- 32 port ADSL board over pots
					 bnameADLH(624),                 -- 32 port ADSL board over pots
					 bnameADLJ(625),                 -- 32 port ADSL board over pots
					 bnameADLK(626),                 -- 32 port ADSL board over pots
					 bnameADLL(627),                 -- 32 port ADSL board over pots
					 bnameADLM(628),                 -- 32 port ADSL board over pots
					 bnameADLN(629),                 -- 32 port ADSL board over pots
					 bnameADLO(630),                 -- 32 port ADSL board over pots
					 bnameADLP(631),                 -- 32 port ADSL board over pots
					 bnameADLQ(632),                 -- 32 port ADSL board over pots
					 bnameADLR(633),                 -- 32 port ADSL board over pots
					 bnameADLS(634),                 -- 32 port ADSL board over pots
					 bnameADLT(635),                 -- 32 port ADSL board over pots
					 bnameADLU(636),                 -- 32 port ADSL board over pots
					 bnameADLV(637),                 -- 32 port ADSL board over pots
					 bnameADLW(638),                 -- 32 port ADSL board over pots
					 bnameADLX(639),                 -- 32 port ADSL board over pots
					 bnameADLY(640),                 -- 32 port ADSL board over pots
					 bnameADLZ(641),                 -- 32 port ADSL board over pots
					 bnameADC(642),                  -- 32 port ADSL2+ board over pots
					 bnameADCA(643),                 -- 32 port ADSL2+ board over pots
					 bnameADCB(644),                 -- 32 port ADSL2+ board over pots
					 bnameADCC(645),                 -- 32 port ADSL2+ board over pots
					 bnameADCD(646),                 -- 32 port ADSL2+ board over pots
					 bnameADCE(647),                 -- 32 port ADSL2+ board over pots
					 bnameADCF(648),                 -- 32 port ADSL2+ board over pots
					 bnameADCG(649),                 -- 32 port ADSL2+ board over pots
					 bnameADCH(650),                 -- 32 port ADSL2+ board over pots
					 bnameADCI(651),                 -- 32 port ADSL2+ board over pots
					 bnameADCJ(652),                 -- 32 port ADSL2+ board over pots
					 bnameADCK(653),                 -- 32 port ADSL2+ board over pots
					 bnameADCL(654),                 -- 32 port ADSL2+ board over pots
					 bnameADCM(655),                 -- 32 port ADSL2+ board over pots
					 bnameADCN(656),                 -- 32 port ADSL2+ board over pots
					 bnameADCO(657),                 -- 32 port ADSL2+ board over pots
					 bnameADCP(658),                 -- 32 port ADSL2+ board over pots
					 bnameADCQ(659),                 -- 32 port ADSL2+ board over pots
					 bnameADCR(660),                 -- 32 port ADSL2+ board over pots
					 bnameADCS(661),                 -- 32 port ADSL2+ board over pots
					 bnameADCT(662),                 -- 32 port ADSL2+ board over pots
					 bnameADCU(663),                 -- 32 port ADSL2+ board over pots
					 bnameADCV(664),                 -- 32 port ADSL2+ board over pots
					 bnameADCW(665),                 -- 32 port ADSL2+ board over pots
					 bnameADCX(666),                 -- 32 port ADSL2+ board over pots
					 bnameADCY(667),                 -- 32 port ADSL2+ board over pots
					 bnameADCZ(668),                 -- 32 port ADSL2+ board over pots
					 bnameADI(669),                  -- 32 port ADSL2+ board over ISDN
					 bnameADID(670),                 -- 32 port ADSL2+ board over ISDN
					 bnameADIE(671),                 -- 32 port ADSL2+ board over ISDN
					 bnameADIF(672),                 -- 32 port ADSL2+ board over ISDN
					 bnameADIH(673),                 -- 32 port ADSL2+ board over ISDN
					 bnameADIJ(674),                 -- 32 port ADSL2+ board over ISDN
					 bnameADIK(675),                 -- 32 port ADSL2+ board over ISDN
					 bnameADIM(676),                 -- 32 port ADSL2+ board over ISDN
					 bnameADIA(677),                 -- 32 port ADSL2+ board over pots
					 bnameADIB(678),                 -- 32 port ADSL2+ board over pots
					 bnameADIC(679),                 -- 32 port ADSL2+ board over pots
					 bnameADIG(680),                 -- 32 port ADSL2+ board over pots
					 bnameADII(681),                 -- 32 port ADSL2+ board over pots
					 bnameADIL(682),                 -- 32 port ADSL2+ board over pots
					 bnameADIN(683),                 -- 32 port ADSL2+ board over pots
					 bnameADIO(684),                 -- 32 port ADSL2+ board over pots
					 bnameADIP(685),                 -- 32 port ADSL2+ board over pots
					 bnameADIQ(686),                 -- 32 port ADSL2+ board over pots
					 bnameADIR(687),                 -- 32 port ADSL2+ board over pots
					 bnameADIS(688),                 -- 32 port ADSL2+ board over pots
					 bnameADIT(689),                 -- 32 port ADSL2+ board over pots
					 bnameADIU(690),                 -- 32 port ADSL2+ board over pots
					 bnameADIV(691),                 -- 32 port ADSL2+ board over pots
					 bnameADIW(692),                 -- 32 port ADSL2+ board over pots
					 bnameADIX(693),                 -- 32 port ADSL2+ board over pots
					 bnameADIY(694),                 -- 32 port ADSL2+ board over pots
					 bnameADIZ(695),                 -- 32 port ADSL2+ board over pots
					 bnameADM(696),                  -- 64 port ADSL2+ board over pots
					 bnameADMA(697),                 -- 64 port ADSL2+ board over pots
					 bnameADMB(698),                 -- 64 port ADSL2+ board over pots
					 bnameADMC(699),                 -- 64 port ADSL2+ board over pots
					 bnameADMD(700),                 -- 64 port ADSL2+ board over pots
					 bnameADME(701),                 -- 64 port ADSL2+ board over pots
					 bnameADMF(702),                 -- 64 port ADSL2+ board over pots
					 bnameADMG(703),                 -- 64 port ADSL2+ board over pots
					 bnameADMH(704),                 -- 64 port ADSL2+ board over pots
					 bnameADMI(705),                 -- 64 port ADSL2+ board over pots
					 bnameADMJ(706),                 -- 64 port ADSL2+ board over pots
					 bnameADMK(707),                 -- 64 port ADSL2+ board over pots
					 bnameADML(708),                 -- 64 port ADSL2+ board over pots
					 bnameADMM(709),                 -- 64 port ADSL2+ board over pots
					 bnameADMN(710),                 -- 64 port ADSL2+ board over pots
					 bnameADMO(711),                 -- 64 port ADSL2+ board over pots
					 bnameADMP(712),                 -- 64 port ADSL2+ board over pots
					 bnameADMQ(713),                 -- 64 port ADSL2+ board over pots
					 bnameADMR(714),                 -- 64 port ADSL2+ board over pots
					 bnameADMS(715),                 -- 64 port ADSL2+ board over pots
					 bnameADMT(716),                 -- 64 port ADSL2+ board over pots
					 bnameADMU(717),                 -- 64 port ADSL2+ board over pots
					 bnameADMV(718),                 -- 64 port ADSL2+ board over pots
					 bnameADMW(719),                 -- 64 port ADSL2+ board over pots
					 bnameADMX(720),                 -- 64 port ADSL2+ board over pots
					 bnameADMY(721),                 -- 64 port ADSL2+ board over pots
					 bnameADMZ(722),                 -- 64 port ADSL2+ board over pots
					 bnameADD(723),                  -- ADSL2+ board of the ADD series
					 bnameADDA(724),                 -- ADSL2+ board of the ADD series
					 bnameADDB(725),                 -- ADSL2+ board of the ADD series
					 bnameADDC(726),                 -- ADSL2+ board of the ADD series
					 bnameADDD(727),                 -- ADSL2+ board of the ADD series
					 bnameADDE(728),                 -- ADSL2+ board of the ADD series
					 bnameADDF(729),                 -- ADSL2+ board of the ADD series
					 bnameADDG(730),                 -- ADSL2+ board of the ADD series
					 bnameADDH(731),                 -- ADSL2+ board of the ADD series
					 bnameADDI(732),                 -- ADSL2+ board of the ADD series
					 bnameADDJ(733),                 -- ADSL2+ board of the ADD series
					 bnameADDK(734),                 -- ADSL2+ board of the ADD series
					 bnameADDL(735),                 -- ADSL2+ board of the ADD series
					 bnameADDM(736),                 -- ADSL2+ board of the ADD series
					 bnameADDN(737),                 -- ADSL2+ board of the ADD series
					 bnameADDO(738),                 -- ADSL2+ board of the ADD series
					 bnameADDP(739),                 -- ADSL2+ board of the ADD series
					 bnameADDQ(740),                 -- ADSL2+ board of the ADD series
					 bnameADDR(741),                 -- ADSL2+ board of the ADD series
					 bnameADDS(742),                 -- ADSL2+ board of the ADD series
					 bnameADDT(743),                 -- ADSL2+ board of the ADD series
					 bnameADDU(744),                 -- ADSL2+ board of the ADD series
					 bnameADDV(745),                 -- ADSL2+ board of the ADD series
					 bnameADDW(746),                 -- ADSL2+ board of the ADD series
					 bnameADDX(747),                 -- ADSL2+ board of the ADD series
					 bnameADDY(748),                 -- ADSL2+ board of the ADD series
					 bnameADDZ(749),                 -- ADSL2+ board of the ADD series
					 bnameH601APMB(750),             -- Control board APMB of the UA5000
					 bnameH601APSB(751),             -- Control board of the local slave Frame of the UA5000
					 bnameH601APSR(752),             -- Control board of the remote slave Frame of the UA5000
					 bnameH561SCU(753),              -- H511SCUA control board of the MA5600. This board supports the PHY/LSW subboard.
					 bnameH601IPMB(754),             -- IPMP control board of the UA5000
					 bnameH533ECBD(755),             -- 64-port GE bus ADSL2+ board (CoronaG)
					 bnameH512ADME(756),             -- 64-port double CELLBUS bus ADSL2+ board (AC7 chipset)
-- UA
					 bnameH601CSMB(757),             -- UA5000 ADSL2+ board
					 bnameH601EAUA(758),             -- 16-port VDSL board of the UA5000
					 bnameH601TSSB(759),             -- Broadband test board of the UA5000
					 bnameH601BP2B(760),             -- UA5000 BPON

					 bnameADE(761),               --ADSL2+ board of the ADE series
					 bnameADEA(762),              --ADSL2+ board of the ADE series
					 bnameADEB(763),              --ADSL2+ board of the ADE series
					 bnameADEC(764),              --ADSL2+ board of the ADE series
					 bnameADED(765),              --ADSL2+ board of the ADE series
					 bnameADEE(766),              --ADSL2+ board of the ADE series
					 bnameADEF(767),              --ADSL2+ board of the ADE series
					 bnameADEG(768),              --ADSL2+ board of the ADE series
					 bnameADEH(769),              --ADSL2+ board of the ADE series
					 bnameADEI(770),              --ADSL2+ board of the ADE series
					 bnameADEJ(771),              --ADSL2+ board of the ADE series
					 bnameADEK(772),              --ADSL2+ board of the ADE series
					 bnameADEL(773),              --ADSL2+ board of the ADE series
					 bnameADEM(774),              --ADSL2+ board of the ADE series
					 bnameADEN(775),              --ADSL2+ board of the ADE series
					 bnameADEO(776),              --ADSL2+ board of the ADE series
					 bnameADEP(777),              --ADSL2+ board of the ADE series
					 bnameADEQ(778),              --ADSL2+ board of the ADE series
					 bnameADER(779),              --ADSL2+ board of the ADE series
					 bnameADES(780),              --ADSL2+ board of the ADE series
					 bnameADET(781),              --ADSL2+ board of the ADE series
					 bnameADEU(782),              --ADSL2+ board of the ADE series
					 bnameADEV(783),              --ADSL2+ board of the ADE series
					 bnameADEW(784),              --ADSL2+ board of the ADE series
					 bnameADEX(785),              --ADSL2+ board of the ADE series
					 bnameADEY(786),              --ADSL2+ board of the ADE series
					 bnameADEZ(787),              --ADSL2+ board of the ADE series

					 bnameH602CSMB(788),             -- 16-port ADSL2+ broadband and narrowband combo board of the UA5000
					 bnameH603CSMC(789),             -- UA5000 ADSL2+ board
					 bnameH601ADRB(790),             -- 32-port ADSL2+ board (with a built-in splitter) of the UA5000
					 bnameH801X1CA(795),              -- 10 GE optical interface board of the OFA5920

-- MA5300:
					 bnameH531EBDC(800),             -- 48-port ADSL over POTS service board (with the built-in splitter)
					 bnameH531EBDI(801),             -- 48-port ADSL over ISDN service board (with the built-in splitter)
					 bnameH531EADI(802),             -- 48-port ADSL over ISDN service board
					 bnameH531EADK(803),             -- 48-port ADSL over ISDN + protection service board
					 bnameH531EBDL(804),             -- 24-port ADSL2+ service board
-- PVU
					 bnamePVU8(1000),                -- H601PVU
					 bnamePVU4(1001),                -- H601PVU
-- RSU
					 bnameRSUA(1002),             --H601RSUA, which provides eight E1 ports
					 bnameRSUA4(1003),            --H601RSUA, which provides four E1 ports
					 bnameH602PWX2(1100),            -- H602PWX2

-- 8060
					 bnameDEVUNKNOWN(3700),
					 bnameDEVRPU(3701),            -- RPU without NP
					 bnameDEVNPRPU(3702),          -- RPU with NP (256M RAM)
					 bnameDEVNP(3703),             -- NPU
					 bnameDEV6FAN(3704),           -- Board with 6 fans
					 bnameDEV8FAN(3705),           -- Board with 8 fans
					 bnameDEVPOWER(3706),          -- Power module
					 bnameDEVRPUE(3707),           -- RPUE without NP
					 bnameDEVNPRPUE(3708),         -- RPUE with NP (512M RAM)
					 bnameDEVCOPE(3709),           -- COP card
					 bnameDEVCF(3710),             -- CF card
					 bnameE200EFAN(3711),
					 bnameE200EPWRAC(3712),
					 bnameE200EPWRDC(3713),
					 fnameE200E(3714),
					 bnameE200ERPU(3715),
					 bnameE100ERPU(3716),
					 bnameUSG3040MBD(3717),
					 bnameEXIFE2GE(3718),

					 bnameDEVH2FE(3719),           -- HIC 2FE
					 bnameDEVHG1GE(3720),          -- 1GE
					 bnameDEVHG2GE(3721),          -- 2GE
					 bnameDEVH4FE(3722),           -- HIC 4FE
					 bnameDEVH8FE(3723),           -- HIC 8FE
					 bnameDEVH1POS(3724),          -- 1POS
					 bnameDEVH2POS(3725),          -- 2POS
					 bnameDEVH4POS(3726),          -- 4POS
					 bnameDEVH2FEP(3727),          -- 2FEP
					 bnameDEVH4FEP(3728),          -- 4FEP
					 bnameDEVH8FEP(3729),          -- 8FEP
					 bnameDEVLCPOS(3730),          -- CPOS
					 bnameDEVHIPSEC(3731),         -- HIC IPSEC
					 bnameDEVHBYPASS(3732),        -- BYPass
					 bnameEXIFE2FE(3733),          -- Dual port Fast Ethernet Card
					 bnameUSG50RPU(3734),          -- Main Processing Unit
					 bnameFW11USBC(3735),          -- Universal Serial Bus Interface Card
					 bnameFW41HPSEC(3736),         -- High Speed IP Security Card C
					 bnameFW41HPSEA(3737),         -- High Speed IP Security Card A
					 bnameFW41GEBY(3738),          -- Gigabit Ethernet Card with Bypass Function
					 bnameFW11EPSEA(3739),         -- Enhanced IP Security Card A
					 bnameRTM1GEUB(3740),          -- 1-Port 1000M Ethernet Electrical Interface Board(RJ45)
					 bnameRTM1GEUA(3741),          -- 1-Port 1000BASE-SX Gigabit Ethernet Interface Board(SFP)
					 bnameFW11EPSEC(3742),         -- Enhanced IP Security Card
					 bnameFW1IPSEC0(3743),         -- IP Security Card
					 bnameFW111AMM0(3744),         -- 1-Port ATM/155M Multimode Interface Module(SC)
					 bnameFW111ASM0(3745),         -- 1-Port ATM/155M Single Mode Interface Module(1310nm,15km,SC)
					 bnameFW111ADP0(3746),         -- 1-Port ADSL over POTS Interface Board

					 bnameDEVLATME1(3749),         -- ATM E1
					 bnameDEVLATME3(3750),         -- ATM E3
					 bnameDEVLATM(3751),           -- ATM Multimode
					 bnameDEVL4SA(3752),           -- 4SA
					 bnameDEVLGSFE(3753),          -- 10/100 SingleMode FE
					 bnameDEVLGMFE(3754),          -- 10/100 MultiMode FE
					 bnameDEVLGGE(3755),           -- FIC GE(Fiber)
					 bnameDEVLDGE(3756),           -- FIC GE(Copper)
					 bnameDEVL1FE(3757),           -- 1FE
					 bnameDEVL2FE(3758),           -- 2FE
					 bnameDEVL8E1A(3759),          -- 8E1A
					 bnameDEVL8E1B(3760),          -- 8E1B
					 bnameDEVL8CE1A(3761),         -- 8CE1A
					 bnameDEVL8CE1B(3762),         -- 8CE1B
					 bnameDEVL8CT1A(3763),         -- 8CT1A
					 bnameDEVL8CT1B(3764),         -- 8CT1B
					 bnameDEVL4CE1A(3765),         -- 4CE1A
					 bnameDEVL4CE1B(3766),         -- 4CE1B
					 bnameDEVL4E1A(3767),          -- 4E1A
					 bnameDEVL4E1B(3768),          -- 4E1B
					 bnameDEVL4CT1A(3769),         -- 4CT1A
					 bnameDEVL4CT1B(3770),         -- 4CT1B
					 bnameDEVL4E1(3771),           -- 4E1
					 bnameDEVL4CE1(3772),          -- 4CE1
					 bnameDEVL4CT1(3773),          -- 4CT1
					 bnameDEVL8T1(3774),           -- 8T1
					 bnameDEVL1CT3(3775),          -- 1CT3
					 bnameDEVL1CE3(3776),          -- 1CE3
					 bnameDEVLIPSEC(3777),
					 bnameDEVL1HSSI(3778),         -- 1HSSI
					 bnameDEVL2HSSI(3779),         -- 2HSSI
					 bnameDEVH16CE1A(3780),        -- 16CE1(120 Ohm)
					 bnameDEVH16CE1B(3781),        -- 16CE1(75 Ohm)
					 bnameDEVH16CT1(3782),         -- 16CT1(120 Ohm)
					 bnameDEVHCPE1(3783),          -- 1CPOSE1(ESFP)
					 bnameDEVHCPT1(3784),          -- 1CPOST1(ESFP)
					 bnameDEVH1ATM(3785),          -- HIC 1ATM(ESFP)
					 bnameDEVH2ATM(3786),          -- HIC 2ATM(ESFP)
					 bnameDEVH4ATM(3787),          -- HIC 4ATM(ESFP)
					 bnameDEVLCT3(3788),             -- 1-port T3/CT3 low-rate interface board
					 bnameDEVLE8I(3789),             -- 8-port IMA E1 low-rate interface board (75 ohms)
					 bnameDEVLE8IA(3790),            -- 8-port IMA E1 low-rate interface board (120 ohms)
					 bnameDEVLT8I(3791),             -- 8-port IMA T1 low-rate interface board
					 bnameDEVLIPSECSD707(3792),    -- FIC IPSEC(SD707)
					 bnameNE20RPU(3793),           -- NE20 RPU (512M RAM)
					 bnameNE20ERPU(3794),          -- NE20E RPU (1G RAM)
					 bnameNE20ENPU(3795),          -- NE20E NPU
					 bnameNE20EFAN(3796),          -- NE20E FAN
					 bnameNE20EPOWERAC(3797),      -- NE20E AC POWER
					 bnameNE20EPOWERDC(3798),      -- NE20E DC POWER
					 bnameDEVLATMSM(3799),         -- ATM Singlemode
					 bnameDEVLATMSL(3800),         -- ATM Singlemode Long Reach
					 bnameDEVHG2GESFPCOPR(3810),   -- 2GE SFP&COPR
					 bnameDEVH3E3(3811),           -- HIC 3E3
					 bnameDEVH3T3(3812),           -- HIC 3T3
					 bnameDEVH8GEF(3813),           -- HIC 8GE COPER
					 bnameDEVH8GFF(3814),           -- HIC 8GE SFP

-- MA5100
					 bnameH563ECBD(131082),          -- 64-port ADSL2+ board

					 bnameH561EIUB(131083),             -- EIUB board

					 bnameADB(131084),               --ADSL2+ board of the ADB series
					 bnameH561ADBA(131085),              --ADSL2+ board of the ADB series
					 bnameH561ADBB(131086),              --ADSL2+ board of the ADB series
					 bnameH561ADBC(131087),              --ADSL2+ board of the ADB series
					 bnameH561ADBD(131088),              --ADSL2+ board of the ADB series
					 bnameH561ADBE(131089),              --ADSL2+ board of the ADB series
					 bnameH561ADBF(131090),              --ADSL2+ board of the ADB series
					 bnameH561ADBG(131091),              --ADSL2+ board of the ADB series
					 bnameH561ADBH(131092),              --ADSL2+ board of the ADB series
					 bnameH561ADBI(131093),              --ADSL2+ board of the ADB series
					 bnameH561ADBJ(131094),              --ADSL2+ board of the ADB series
					 bnameH561ADBK(131095),              --ADSL2+ board of the ADB series
					 bnameH561ADBL(131096),              --ADSL2+ board of the ADB series
					 bnameH561ADBM(131097),              --ADSL2+ board of the ADB series
					 bnameH561ADBN(131098),              --ADSL2+ board of the ADB series
					 bnameH561ADBO(131099),              --ADSL2+ board of the ADB series
					 bnameH561ADBP(131100),              --ADSL2+ board of the ADB series
					 bnameH561ADBQ(131101),              --ADSL2+ board of the ADB series
					 bnameH561ADBR(131102),              --ADSL2+ board of the ADB series
					 bnameH561ADBS(131103),              --ADSL2+ board of the ADB series
					 bnameH561ADBT(131104),              --ADSL2+ board of the ADB series
					 bnameH561ADBU(131105),              --ADSL2+ board of the ADB series
					 bnameH561ADBV(131106),              --ADSL2+ board of the ADB series
					 bnameH561ADBW(131107),              --ADSL2+ board of the ADB series
					 bnameH561ADBX(131108),              --ADSL2+ board of the ADB series
					 bnameH561ADBY(131109),              --ADSL2+ board of the ADB series
					 bnameH561ADBZ(131110),              --ADSL2+ board of the ADB series

					 bnameH561SHEA(131111),              --H561SHEA service board of the MA5600. This board uses the GE bus and provides 32 ports
					 bnameH561SCUK(131112),              -- SCUK control board of the MA5600. Compared with the SCUA control board,
																	 -- the SCUK control board does not provide the LSW/PHY subboard and the clock subboard.

					 bnameADG(131113),               -- 32-port GE bus ADSL2+ board of the ADG series
					 bnameADGA(131114),              -- 32-port GE bus ADSL2+ board of the ADG series
					 bnameADGB(131115),              -- 32-port GE bus ADSL2+ board of the ADG series
					 bnameADGC(131116),              -- 32-port GE bus ADSL2+ board of the ADG series
					 bnameADGD(131117),              -- 32-port GE bus ADSL2+ board of the ADG series
					 bnameADGE(131118),              -- 32-port GE bus ADSL2+ board of the ADG series
					 bnameADGF(131119),              -- 32-port GE bus ADSL2+ board of the ADG series
					 bnameADGG(131120),              -- 32-port GE bus ADSL2+ board of the ADG series
					 bnameADGH(131121),              -- 32-port GE bus ADSL2+ board of the ADG series
					 bnameADGI(131122),              -- 32-port GE bus ADSL2+ board of the ADG series
					 bnameADGJ(131123),              -- 32-port GE bus ADSL2+ board of the ADG series
					 bnameADGK(131124),              -- 32-port GE bus ADSL2+ board of the ADG series
					 bnameADGL(131125),              -- 32-port GE bus ADSL2+ board of the ADG series
					 bnameADGM(131126),              -- 32-port GE bus ADSL2+ board of the ADG series
					 bnameADGN(131127),              -- 32-port GE bus ADSL2+ board of the ADG series
					 bnameADGO(131128),              -- 32-port GE bus ADSL2+ board of the ADG series
					 bnameADGP(131129),              -- 32-port GE bus ADSL2+ board of the ADG series
					 bnameADGQ(131130),              -- 32-port GE bus ADSL2+ board of the ADG series
					 bnameADGR(131131),              -- 32-port GE bus ADSL2+ board of the ADG series
					 bnameADGS(131132),              -- 32-port GE bus ADSL2+ board of the ADG series
					 bnameADGT(131133),              -- 32-port GE bus ADSL2+ board of the ADG series
					 bnameADGU(131134),              -- 32-port GE bus ADSL2+ board of the ADG series
					 bnameADGV(131135),              -- 32-port GE bus ADSL2+ board of the ADG series
					 bnameADGW(131136),              -- 32-port GE bus ADSL2+ board of the ADG series
					 bnameADGX(131137),              -- 32-port GE bus ADSL2+ board of the ADG series
					 bnameADGY(131138),              -- 32-port GE bus ADSL2+ board of the ADG series
					 bnameADGZ(131139),              -- 32-port GE bus ADSL2+ board of the ADG series

					 bnameH561VDEA(131140),          -- 64-port GE bus board: VDEA
					 bnameH561AIUG(131141),          -- GE bus AIU board of the MA5600
					 bnameH561SPLF(131142),          -- Passive ADSL2+ over POTS SPL board, with an impedance of 600 ohms
					 bnameH561SPLH(131143),          -- Passive ADSL2+ over ISDN SPL board
					 bnameH561SPLL(131144),          -- Passive ADSL2+ over POTS SPL board, with complex impedance

					 bnameH511ECUA(131150),          -- ECUA control board of the MA5100 V3

					 bnameH511LANE(131151),          -- LANE board of the MA5100
-- MA5105 from 0X20F00 ~0X20Fff
					 bnameH521mfea(134912),          -- FE electric port upstream board, which supports 64 ports
					 bnameH521mfoa(134913),          -- FE optical port upstream board, which supports 64 ports
					 bnameH521mimb(134914),          -- IMA upstream board, which supports 64 ports
					 bnameH521mcoa(134915),          -- 155M optical port upstream board, which supports 64 ports
					 bnameH521mgoa(134916),          -- GE optical port upstream board, which supports 64 ports
					 bnameH523adla(134928),          -- ADLA board, which supports 16 ports

--  MA5200 add definitiong of board type 0x21000(135168) ~ 0x21FFF(139263)
					 bnameH521SMU(135168),
					 bnameH521CLK(135169),
					 bnameH521PWR(135170),
					 bnameH521DPR(135171),
					 bnameH521FAN(135172),
					 bnameH521DRYPWR(135173),
					 bnameH521DRYFAN(135174),
					 bnameH521SFU(135175),
					 bnameH521SFUF(135176),
					 bnameH521SSU(135177),
					 bnameH521SPU(135178),
					 bnameH522SFUT(135179),
					 bnameH522SPUT(135180),
					 bnameH522SSUT(135181),
					 bnameH522SPUF(135182),
					 bnameH522SSUF(135183),
					 bnameH521SMUE(135184),
					 bnameH523SMUG(135185),
					 bnameH521NSBD(135186),
					 bnameH523SFUG(135187),
-- MA5600

					 bnameH801SCUA(143360),          -- Broadband control board H801SCUA of the P300
					 bnameH801SPLK(143361),          -- SPL board H801SPLK of the P300
					 bnameH801SPMA(143362),          -- Control board of the SPL series boards of the P300
					 bnameH805ADLL(143363),          -- P300 ADSL board
					 bnameH802SHLA(143364),          -- SHDSL board H802SHLA of the P300
					 bnameH801AIUG(143365),          -- ATM interface board H801AIUG of the P300

					 bnameADI2(143366),               -- P300 32-channel ADSL boards of the ADI series
					 bnameADIA2(143367),          -- P300 32-channel ADSL board of the ADI series
					 bnameADIB2(143368),          -- P300 32-channel ADSL board of the ADI series
					 bnameADIC2(143369),          -- P300 32-channel ADSL board of the ADI series
					 bnameADID2(143370),          -- P300 32-channel ADSL board of the ADI series
					 bnameADIE2(143371),          -- P300 32-channel ADSL board of the ADI series
					 bnameADIF2(143372),          -- P300 32-channel ADSL board of the ADI series
					 bnameADIG2(143373),          -- P300 32-channel ADSL board of the ADI series
					 bnameADIH2(143374),          -- P300 32-channel ADSL board of the ADI series
					 bnameADII2(143375),          -- P300 32-channel ADSL board of the ADI series
					 bnameADIJ2(143376),          -- P300 32-channel ADSL board of the ADI series
					 bnameADIK2(143377),          -- P300 32-channel ADSL board of the ADI series
					 bnameADIM2(143378),          -- P300 32-channel ADSL board of the ADI series
					 bnameADIN2(143379),          -- P300 32-channel ADSL board of the ADI series
					 bnameADIL2(143380),          -- P300 32-channel ADSL board of the ADI series
					 bnameADIO2(143381),          -- P300 32-channel ADSL board of the ADI series
					 bnameADIP2(143382),          -- P300 32-channel ADSL board of the ADI series
					 bnameADIQ2(143383),          -- P300 32-channel ADSL board of the ADI series
					 bnameADIR2(143384),          -- P300 32-channel ADSL board of the ADI series
					 bnameADIS2(143385),          -- P300 32-channel ADSL board of the ADI series
					 bnameADIT2(143386),          -- P300 32-channel ADSL board of the ADI series
					 bnameADIU2(143387),          -- P300 32-channel ADSL board of the ADI series
					 bnameADIV2(143388),          -- P300 32-channel ADSL board of the ADI series
					 bnameADIW2(143389),          -- P300 32-channel ADSL board of the ADI series
					 bnameADIX2(143390),          -- P300 32-channel ADSL board of the ADI series
					 bnameADIY2(143391),          -- P300 32-channel ADSL board of the ADI series
					 bnameADIZ2(143392),          -- P300 32-channel ADSL board of the ADI series

					 bnameADL2(143393),                -- P300 32-channel ADSL board of the ADL series
					 bnameADLA2(143394),           -- P300 32-channel ADSL board of the ADL series
					 bnameADLB2(143395),           -- P300 32-channel ADSL board of the ADL series
					 bnameADLC2(143396),           -- P300 32-channel ADSL board of the ADL series
					 bnameADLD2(143397),           -- P300 32-channel ADSL board of the ADL series
					 bnameADLE2(143398),           -- P300 32-channel ADSL board of the ADL series
					 bnameADLF2(143399),           -- P300 32-channel ADSL board of the ADL series
					 bnameADLG2(143400),           -- P300 32-channel ADSL board of the ADL series
					 bnameADLH2(143401),           -- P300 32-channel ADSL board of the ADL series
					 bnameADLI2(143402),           -- P300 32-channel ADSL board of the ADL series
					 bnameADLJ2(143403),           -- P300 32-channel ADSL board of the ADL series
					 bnameADLK2(143404),           -- P300 32-channel ADSL board of the ADL series
					 bnameADLM2(143405),           -- P300 32-channel ADSL board of the ADL series
					 bnameADLN2(143406),           -- P300 32-channel ADSL board of the ADL series
					 bnameADLO2(143407),           -- P300 32-channel ADSL board of the ADL series
					 bnameADLP2(143408),           -- P300 32-channel ADSL board of the ADL series
					 bnameADLQ2(143409),           -- P300 32-channel ADSL board of the ADL series
					 bnameADLR2(143410),           -- P300 32-channel ADSL board of the ADL series
					 bnameADLS2(143411),           -- P300 32-channel ADSL board of the ADL series
					 bnameADLT2(143412),           -- P300 32-channel ADSL board of the ADL series
					 bnameADLU2(143413),           -- P300 32-channel ADSL board of the ADL series
					 bnameADLV2(143414),           -- P300 32-channel ADSL board of the ADL series
					 bnameADLW2(143415),           -- P300 32-channel ADSL board of the ADL series
					 bnameADLX2(143416),           -- P300 32-channel ADSL board of the ADL series
					 bnameADLY2(143417),           -- P300 32-channel ADSL board of the ADL series
					 bnameADLZ2(143418),           -- P300 32-channel ADSL board of the ADL series

					 bnameSHD(143419),            -- P300 16-channel GDOT boards of the SHD series
					 bnameSHDA(143420),           -- P300 16-channel GDOT board of the SHD series
					 bnameSHDB(143421),           -- P300 16-channel GDOT board of the SHD series
					 bnameSHDC(143422),           -- P300 16-channel GDOT board of the SHD series
					 bnameSHDD(143423),           -- P300 16-channel GDOT board of the SHD series
					 bnameSHDE(143424),           -- P300 16-channel GDOT board of the SHD series
					 bnameSHDF(143425),           -- P300 16-channel GDOT board of the SHD series
					 bnameSHDG(143426),           -- P300 16-channel GDOT board of the SHD series
					 bnameSHDH(143427),           -- P300 16-channel GDOT board of the SHD series
					 bnameSHDI(143428),           -- P300 16-channel GDOT board of the SHD series
					 bnameSHDJ(143429),           -- P300 16-channel GDOT board of the SHD series
					 bnameSHDK(143430),           -- P300 16-channel GDOT board of the SHD series
					 bnameSHDL(143431),           -- P300 16-channel GDOT board of the SHD series
					 bnameSHDM(143432),           -- P300 16-channel GDOT board of the SHD series
					 bnameSHDN(143433),           -- P300 16-channel GDOT board of the SHD series
					 bnameSHDO(143434),           -- P300 16-channel GDOT board of the SHD series
					 bnameSHDP(143435),           -- P300 16-channel GDOT board of the SHD series
					 bnameSHDQ(143436),           -- P300 16-channel GDOT board of the SHD series
					 bnameSHDR(143437),           -- P300 16-channel GDOT board of the SHD series
					 bnameSHDS(143438),           -- P300 16-channel GDOT board of the SHD series
					 bnameSHDT(143439),           -- P300 16-channel GDOT board of the SHD series
					 bnameSHDU(143440),           -- P300 16-channel GDOT board of the SHD series
					 bnameSHDV(143441),           -- P300 16-channel GDOT board of the SHD series
					 bnameSHDW(143442),           -- P300 16-channel GDOT board of the SHD series
					 bnameSHDX(143443),           -- P300 16-channel GDOT board of the SHD series
					 bnameSHDY(143444),           -- P300 16-channel GDOT board of the SHD series
					 bnameSHDZ(143445),           -- P300 16-channel GDOT board of the SHD series
					 bnameH80ASHLM(143446),       -- P300 16-channel GDOT board
					 bnameSHG(143447),            -- P300 32-channel G.SHDSL board of the SHG series
					 bnameADK(143500),            -- P300 64-channel ADSL2 board of the ADK series
					 bnameH521mcca(143600),       -- Control board of the MA5605. This board provides 155M optical port in upstream,
															-- provides 64 channels, and supports subtending.

					 bnameH801SPLG1(143700),      -- Board in the P300 SPL Frame. This board is used to separate the ADSL
															-- signals from the POTS signals. Its function is similar to the function
															-- of H801SPLK or H801SPLG2.
					 bnameH801SPLG2(143701),      -- Board in the P300 SPL Frame. This board is used to separate the ADSL signals
															-- from the POTS signals. Its function is similar to the function of H801SPLK or H801SPLG1.
					 bnameH801BSPA(143702),       -- Board in the P300 SPL Frame. This board is used to realize the N+1 backup of boards.

					 bnameVDL(143703),        -- P300 32-channel boards of the VDSL series
					 bnameVDLA(143704),        -- P300 32-channel board of the VDSL series
					 bnameVDLB(143705),        -- P300 32-channel board of the VDSL series
					 bnameVDLC(143706),        -- P300 32-channel board of the VDSL series
					 bnameVDLD(143707),        -- P300 32-channel board of the VDSL series
					 bnameVDLE(143708),        -- P300 32-channel board of the VDSL series
					 bnameVDLF(143709),        -- P300 32-channel board of the VDSL series
					 bnameVDLG(143710),        -- P300 32-channel board of the VDSL series
					 bnameVDLH(143711),        -- P300 32-channel board of the VDSL series
					 bnameVDLI(143712),        -- P300 32-channel board of the VDSL series
					 bnameVDLJ(143713),        -- P300 32-channel board of the VDSL series
					 bnameVDLK(143714),        -- P300 32-channel board of the VDSL series
					 bnameVDLL(143715),        -- P300 32-channel board of the VDSL series
					 bnameVDLM(143716),        -- P300 32-channel board of the VDSL series
					 bnameVDLN(143717),        -- P300 32-channel board of the VDSL series
					 bnameVDLO(143718),        -- P300 32-channel board of the VDSL series
					 bnameVDLP(143719),        -- P300 32-channel board of the VDSL series
					 bnameVDLQ(143720),        -- P300 32-channel board of the VDSL series
					 bnameVDLR(143721),        -- P300 32-channel board of the VDSL series
					 bnameVDLS(143722),        -- P300 32-channel board of the VDSL series
					 bnameVDLT(143723),        -- P300 32-channel board of the VDSL series
					 bnameVDLU(143724),        -- P300 32-channel board of the VDSL series
					 bnameVDLV(143725),        -- P300 32-channel board of the VDSL series
					 bnameVDLW(143726),        -- P300 32-channel board of the VDSL series
					 bnameVDLX(143727),        -- P300 32-channel board of the VDSL series
					 bnameVDLY(143728),        -- P300 32-channel board of the VDSL series
					 bnameVDLZ(143729),        -- P300 32-channel board of the VDSL series

					 bnameH803CVD(143730),         -- P300 16-channel boards of the VDSL series
					 bnameH803CVDA(143731),        -- P300 16-channel board of the VDSL series
					 bnameH803CVDB(143732),        -- P300 16-channel board of the VDSL series
					 bnameH803CVDC(143733),        -- P300 16-channel board of the VDSL series
					 bnameH803CVDD(143734),        -- P300 16-channel board of the VDSL series
					 bnameH803CVDE(143735),        -- P300 16-channel board of the VDSL series
					 bnameH803CVDF(143736),        -- P300 16-channel board of the VDSL series
					 bnameH803CVDG(143737),        -- P300 16-channel board of the VDSL series
					 bnameH803CVDH(143738),        -- P300 16-channel board of the VDSL series
					 bnameH803CVDI(143739),        -- P300 16-channel board of the VDSL series
					 bnameH803CVDJ(143740),        -- P300 16-channel board of the VDSL series
					 bnameH803CVDK(143741),        -- P300 16-channel board of the VDSL series
					 bnameH803CVDL(143742),        -- P300 16-channel board of the VDSL series
					 bnameH803CVDM(143743),        -- P300 16-channel board of the VDSL series
					 bnameH803CVDN(143744),        -- P300 16-channel board of the VDSL series
					 bnameH803CVDO(143745),        -- P300 16-channel board of the VDSL series
					 bnameH803CVDP(143746),        -- P300 16-channel board of the VDSL series
					 bnameH803CVDQ(143747),        -- P300 16-channel board of the VDSL series
					 bnameH803CVDR(143748),        -- P300 16-channel board of the VDSL series
					 bnameH803CVDS(143749),        -- P300 16-channel board of the VDSL series
					 bnameH803CVDT(143750),        -- P300 16-channel board of the VDSL series
					 bnameH803CVDU(143751),        -- P300 16-channel board of the VDSL series
					 bnameH803CVDV(143752),        -- P300 16-channel board of the VDSL series
					 bnameH803CVDW(143753),        -- P300 16-channel board of the VDSL series
					 bnameH803CVDX(143754),        -- P300 16-channel board of the VDSL series
					 bnameH803CVDY(143755),        -- P300 16-channel board of the VDSL series
					 bnameH803CVDZ(143756),        -- P300 16-channel board of the VDSL series

					 bnameH805CAN(143757),         -- P300 KPN 16-channel board of the ADSL series
					 bnameH805CANA(143758),        -- P300 KPN 16-channel board of the ADSL series
					 bnameH805CANB(143759),        -- P300 KPN 16-channel board of the ADSL series
					 bnameH805CANC(143760),        -- P300 KPN 16-channel board of the ADSL series
					 bnameH805CAND(143761),        -- P300 KPN 16-channel board of the ADSL series
					 bnameH805CANE(143762),        -- P300 KPN 16-channel board of the ADSL series
					 bnameH805CANF(143763),        -- P300 KPN 16-channel board of the ADSL series
					 bnameH805CANG(143764),        -- P300 KPN 16-channel board of the ADSL series
					 bnameH805CANH(143765),        -- P300 KPN 16-channel board of the ADSL series
					 bnameH805CANI(143766),        -- P300 KPN 16-channel board of the ADSL series
					 bnameH805CANJ(143767),        -- P300 KPN 16-channel board of the ADSL series
					 bnameH805CANK(143768),        -- P300 KPN 16-channel board of the ADSL series
					 bnameH805CANL(143769),        -- P300 KPN 16-channel board of the ADSL series
					 bnameH805CANM(143770),        -- P300 KPN 16-channel board of the ADSL series
					 bnameH805CANN(143771),        -- P300 KPN 16-channel board of the ADSL series
					 bnameH805CANO(143772),        -- P300 KPN 16-channel board of the ADSL series
					 bnameH805CANP(143773),        -- P300 KPN 16-channel board of the ADSL series
					 bnameH805CANQ(143774),        -- P300 KPN 16-channel board of the ADSL series
					 bnameH805CANR(143775),        -- P300 KPN 16-channel board of the ADSL series
					 bnameH805CANS(143776),        -- P300 KPN 16-channel board of the ADSL series
					 bnameH805CANT(143777),        -- P300 KPN 16-channel board of the ADSL series
					 bnameH805CANU(143778),        -- P300 KPN 16-channel board of the ADSL series
					 bnameH805CANV(143779),        -- P300 KPN 16-channel board of the ADSL series
					 bnameH805CANW(143780),        -- P300 KPN 16-channel board of the ADSL series
					 bnameH805CANX(143781),        -- P300 KPN 16-channel board of the ADSL series
					 bnameH805CANY(143782),        -- P300 KPN 16-channel board of the ADSL series
					 bnameH805CANZ(143783),        -- P300 KPN 16-channel board of the ADSL series

					 bnameH805CAL(143784),         -- P300 KPN 32-channel boards of the ADSL series
					 bnameH805CALA(143785),        -- P300 KPN 32-channel board of the ADSL series
					 bnameH805CALB(143786),        -- P300 KPN 32-channel board of the ADSL series
					 bnameH805CALC(143787),        -- P300 KPN 32-channel board of the ADSL series
					 bnameH805CALD(143788),        -- P300 KPN 32-channel board of the ADSL series
					 bnameH805CALE(143789),        -- P300 KPN 32-channel board of the ADSL series
					 bnameH805CALF(143790),        -- P300 KPN 32-channel board of the ADSL series
					 bnameH805CALG(143791),        -- P300 KPN 32-channel board of the ADSL series
					 bnameH805CALH(143792),        -- P300 KPN 32-channel board of the ADSL series
					 bnameH805CALI(143793),        -- P300 KPN 32-channel board of the ADSL series
					 bnameH805CALJ(143794),        -- P300 KPN 32-channel board of the ADSL series
					 bnameH805CALK(143795),        -- P300 KPN 32-channel board of the ADSL series
					 bnameH805CALL(143796),        -- P300 KPN 32-channel board of the ADSL series
					 bnameH805CALM(143797),        -- P300 KPN 32-channel board of the ADSL series
					 bnameH805CALN(143798),        -- P300 KPN 32-channel board of the ADSL series
					 bnameH805CALO(143799),        -- P300 KPN 32-channel board of the ADSL series
					 bnameH805CALP(143800),        -- P300 KPN 32-channel board of the ADSL series
					 bnameH805CALQ(143801),        -- P300 KPN 32-channel board of the ADSL series
					 bnameH805CALR(143802),        -- P300 KPN 32-channel board of the ADSL series
					 bnameH805CALS(143803),        -- P300 KPN 32-channel board of the ADSL series
					 bnameH805CALT(143804),        -- P300 KPN 32-channel board of the ADSL series
					 bnameH805CALU(143805),        -- P300 KPN 32-channel board of the ADSL series
					 bnameH805CALV(143806),        -- P300 KPN 32-channel board of the ADSL series
					 bnameH805CALW(143807),        -- P300 KPN 32-channel board of the ADSL series
					 bnameH805CALX(143808),        -- P300 KPN 32-channel board of the ADSL series
					 bnameH805CALY(143809),        -- P300 KPN 32-channel board of the ADSL series
					 bnameH805CALZ(143810),        -- P300 KPN 32-channel board of the ADSL series

					 bnameH801GICA(143811),        -- P300 KPN general interface board
					 bnameH801GICB(143812),        -- P300 KPN general interface board
					 bnameH801FICA(143813),        -- P300 KPN general interface board
					 bnameH801PRTA(143814),        -- P300 power board H801PRTA
					 bnameH801CITA(143815),        -- P300 cable routing board H801CITA
					 bnameH801PRTS(143816),        -- P300 power board H801PRTS
					 bnameH801CITS(143817),        -- P300 cable routing board H801CITS

					 bnameH80xVDS(143818),         -- P300 24-channel boards of the VDSL2 over POTS series
					 bnameH80xVDSA(143819),        -- P300 24-channel board of the VDSL2 over POTS series
					 bnameH80xVDSB(143820),        -- P300 24-channel board of the VDSL2 over POTS series
					 bnameH80xVDSC(143821),        -- P300 24-channel board of the VDSL2 over POTS series
					 bnameH80xVDSD(143822),        --P300 24-channel board of the VDSL2 over POTS series
					 bnameH80xVDSE(143823),        -- P300 24-channel board of the VDSL2 over POTS series
					 bnameH80xVDSF(143824),        -- P300 24-channel board of the VDSL2 over POTS series
					 bnameH80xVDSG(143825),        -- P300 24-channel board of the VDSL2 over POTS series
					 bnameH80xVDSH(143826),        -- P300 24-channel board of the VDSL2 over POTS series
					 bnameH80xVDSI(143827),        -- P300 24-channel board of the VDSL2 over POTS series
					 bnameH80xVDSJ(143828),        -- P300 24-channel board of the VDSL2 over POTS series
					 bnameH80xVDSK(143829),        -- P300 24-channel board of the VDSL2 over POTS series
					 bnameH80xVDSL(143830),        -- P300 24-channel board of the VDSL2 over POTS series
					 bnameH80xVDSM(143831),        -- P300 24-channel board of the VDSL2 over POTS series
					 bnameH80xVDSN(143832),        -- P300 24-channel board of the VDSL2 over POTS series
					 bnameH80xVDSO(143833),        -- P300 24-channel board of the VDSL2 over POTS series
					 bnameH80xVDSP(143834),        -- P300 24-channel board of the VDSL2 over POTS series
					 bnameH80xVDSQ(143835),        -- P300 24-channel board of the VDSL2 over POTS series
					 bnameH80xVDSR(143836),        -- P300 24-channel board of the VDSL2 over POTS series
					 bnameH80xVDSS(143837),        -- P300 24-channel board of the VDSL2 over POTS series
					 bnameH80xVDST(143838),        -- P300 24-channel board of the VDSL2 over POTS series
					 bnameH80xVDSU(143839),        -- P300 24-channel board of the VDSL2 over POTS series
					 bnameH80xVDSV(143840),        -- P300 24-channel board of the VDSL2 over POTS series
					 bnameH80xVDSW(143841),        -- P300 24-channel board of the VDSL2 over POTS series
					 bnameH80xVDSX(143842),        -- P300 24-channel board of the VDSL2 over POTS series
					 bnameH80xVDSY(143843),        -- P300 24-channel board of the VDSL2 over POTS series
					 bnameH80xVDSZ(143844),        -- P300 24-channel board of the VDSL2 over POTS series

					 bnameH80xVDT(143845),         -- P300 24-channel boards of the VDSL2 over ISDN series
					 bnameH80xVDTA(143846),        -- P300 24-channel board of the VDSL2 over ISDN series
					 bnameH80xVDTB(143847),        -- P300 24-channel board of the VDSL2 over ISDN series
					 bnameH80xVDTC(143848),        -- P300 24-channel board of the VDSL2 over ISDN series
					 bnameH80xVDTD(143849),        -- P300 24-channel board of the VDSL2 over ISDN series
					 bnameH80xVDTE(143850),        -- P300 24-channel board of the VDSL2 over ISDN series
					 bnameH80xVDTF(143851),        -- P300 24-channel board of the VDSL2 over ISDN series
					 bnameH80xVDTG(143852),        -- P300 24-channel board of the VDSL2 over ISDN series
					 bnameH80xVDTH(143853),        -- P300 24-channel board of the VDSL2 over ISDN series
					 bnameH80xVDTI(143854),        -- P300 24-channel board of the VDSL2 over ISDN series
					 bnameH80xVDTJ(143855),        -- P300 24-channel board of the VDSL2 over ISDN series
					 bnameH80xVDTK(143856),        -- P300 24-channel board of the VDSL2 over ISDN series
					 bnameH80xVDTL(143857),        -- P300 24-channel board of the VDSL2 over ISDN series
					 bnameH80xVDTM(143858),        -- P300 24-channel board of the VDSL2 over ISDN series
					 bnameH80xVDTN(143859),        -- P300 24-channel board of the VDSL2 over ISDN series
					 bnameH80xVDTO(143860),        -- P300 24-channel board of the VDSL2 over ISDN series
					 bnameH80xVDTP(143861),        -- P300 24-channel board of the VDSL2 over ISDN series
					 bnameH80xVDTQ(143862),        -- P300 24-channel board of the VDSL2 over ISDN series
					 bnameH80xVDTR(143863),        -- P300 24-channel board of the VDSL2 over ISDN series
					 bnameH80xVDTS(143864),        -- P300 24-channel board of the VDSL2 over ISDN series
					 bnameH80xVDTT(143865),        -- P300 24-channel board of the VDSL2 over ISDN series
					 bnameH80xVDTU(143866),        -- P300 24-channel board of the VDSL2 over ISDN series
					 bnameH80xVDTV(143867),        -- P300 24-channel board of the VDSL2 over ISDN series
					 bnameH80xVDTW(143868),        -- P300 24-channel board of the VDSL2 over ISDN series
					 bnameH80xVDTX(143869),        -- P300 24-channel board of the VDSL2 over ISDN series
					 bnameH80xVDTY(143870),        -- P300 24-channel board of the VDSL2 over ISDN series
					 bnameH80xVDTZ(143871),        -- P300 24-channel board of the VDSL2 over ISDN series
					 bnameH801OPFA(143872),        -- P300 16-channel GE bus Ethernet FE optical access board
					 bnameH801GICD(143873),        -- P300 4GE optical interface upstream board
					 bnameH801GICE(143874),        -- P300 4GE electric interface upstream board
					 bnameH801FICB(143875),        -- P300 FE optical interface upstream board
					 bnameH801HWTF(143876),        -- P300 2GE optical port board for subtending the slave Frame

					 bnameH801MCUA(143877),        -- Broadband control board H801MCUA of the MA5606T
					 bnameH801MPWA(143878),        -- Power board H801MPWA of the MA5606T

					 bnameH801ETHA(143879),        -- Ethernet subtend interface board of the MA5600T
					 bnameH801MFGA(143880),        -- MPLS service board of the MA5600T

					 bnameH801SPLE(143881),         -- SPL boards (with the CPU) of the SPLE series of the MA5600T
					 bnameH801SPLE1(143882),        -- SPL board (with the CPU) of the SPLE series of the MA5600T
					 bnameH801SPLE2(143883),        -- SPL board (with the CPU) of the SPLE series of the MA5600T
					 bnameH801SPLE3(143884),        -- SPL board (with the CPU) of the SPLE series of the MA5600T
					 bnameH801SPLE4(143885),        -- SPL board (with the CPU) of the SPLE series of the MA5600T

					 bnameH801MCUB(143886),        -- Broadband control board for the slave Frame of the MA5606T: H801MCUB

					 bnameH801BIUA(143887),        -- Board of the MA5600T. This board provides two BITS input ports
															 -- and one BITS output port, and supports the optional configuration of the H801CKMA subboard.
					 bnameH802DSRE(143888),        -- 32-channel ISDN service board of the MA5600T
					 bnameH802DSRD(143889),        -- 32-channel ISDN service board of the MA5600T
					 bnameH80XVDR(143890),         -- P300 24 ports VDSL2 OVER POTS series board
					 bnameH801ETHB(143891),        -- Ethernet subtend interface board of the MA5600T
					 bnameH80XVDJ(143892),         -- 48-channel boards of the VDSL series of the MA5600

					 bnameH561EPBA(145920),        -- EPBA board of the OFA5920&MA5600. This board provides 1, 2, or 4 EPON ports.
					 bnameH565VDE(145921),         -- 32-channel boards of the VDSL series of the MA5600
					 bnameH565VDEA(145922),        -- 32-channel board of the VDSL series of the MA5600
					 bnameH565VDEC(145924),        -- 32-channel board of the VDSL series of the MA5600
					 bnameH565VDED(145925),        -- 32-channel board of the VDSL series of the MA5600
					 bnameH565VDEE(145926),        -- 32-channel board of the VDSL series of the MA5600
					 bnameH565VDEF(145927),        -- 32-channel board of the VDSL series of the MA5600
					 bnameH565VDEG(145928),        -- 32-channel board of the VDSL series of the MA5600
					 bnameH565VDEH(145929),        -- 32-channel board of the VDSL series of the MA5600
					 bnameH565VDEI(145930),        -- 32-channel board of the VDSL series of the MA5600
					 bnameH565VDEJ(145931),        -- 32-channel board of the VDSL series of the MA5600
					 bnameH565VDEK(145932),        -- 32-channel board of the VDSL series of the MA5600
					 bnameH565VDEL(145933),        -- 32-channel board of the VDSL series of the MA5600
					 bnameH565VDEM(145934),        -- 32-channel board of the VDSL series of the MA5600
					 bnameH565VDEN(145935),        -- 32-channel board of the VDSL series of the MA5600
					 bnameH565VDEO(145936),        -- 32-channel board of the VDSL series of the MA5600
					 bnameH565VDEP(145937),        -- 32-channel board of the VDSL series of the MA5600
					 bnameH565VDEQ(145938),        -- 32-channel board of the VDSL series of the MA5600
					 bnameH565VDER(145939),        -- 32-channel board of the VDSL series of the MA5600
					 bnameH565VDES(145940),        -- 32-channel board of the VDSL series of the MA5600
					 bnameH565VDET(145941),        -- 32-channel board of the VDSL series of the MA5600
					 bnameH565VDEU(145942),        -- 32-channel board of the VDSL series of the MA5600
					 bnameH565VDEV(145943),        -- 32-channel board of the VDSL series of the MA5600
					 bnameH565VDEW(145944),        -- 32-channel board of the VDSL series of the MA5600
					 bnameH565VDEX(145945),        -- 32-channel board of the VDSL series of the MA5600
					 bnameH565VDEY(145946),        -- 32-channel board of the VDSL series of the MA5600
					 bnameH565VDEZ(145947),        -- 32-channel board of the VDSL series of the MA5600

					 bnameH561ETHA(145948),        -- Ethernet subtend board of the MA5600
					 bnameH801CITD(145949),        -- P300 cable routing board H801CITD
					 bnameH801PRTB(145950),        -- P300 power board H801PRTB

					 bnameH801MCUC(146035),        -- MA5606T Master board H801MCUC
					 bnameH801MPWB(146036),        -- MA5606T DC Power  board H801MPWB
					 bnameH801MPWZ(146053),        -- MA5606T AC Power  board H801MPWZ
					 bnameH80BCAME(146069),        -- 48-channel ADSL2+ and POTS(combo) service board
					 bnameH85BCVME(146070),        -- 48-channel VDSL2+ and POTS(combo) service board
					 bnameH801VRGA(146071),        -- Virtual Route Gateway Board
					 bnameH806EPBD(146072),        -- 8EPON board
					 bnameH801SPUF(146073),        -- interface board.
					 bnameH801MPWD(146074),        -- Power board of MA5608T.
					 bnameH806CAME(146077),        -- 48-channel ADSL combo service board.
					 bnameH801X2CK(146078),        -- 10GE synchronized Ethernet interface board.
					 bnameH80XVDP(146066),         -- 64-channel VDSL2 over POTS service board
					 bnameH801SPUC(155955),        -- interface board.


-- MA5626
					 bnameH821EPUA(145960),        -- Master board of MA5626 Box type device
					 bnameH821EPFA(145961),        -- 24-channel Vitual FE Board of MA5626
					 bnameH821EPFB(145962),        -- 16-channel Vitual FE Board of MA5626
					 bnameH821ASM(145963),         -- 24-channel POTS Board of MA5626
					 bnameH821ASN(145964),         -- 16-channel POTS Board of MA5626
-- MA5651
					 bnameH822VDJF(145965),         -- 16-channel Vitual VDSL2 Board of MA5651
					 bnameH822EVJG(145968),         -- 8-channel Vitual VDSL2 Board of MA5651
-- MA562X
					 bnameH821EPFD(145966),        -- MA562X 8LAN
					 bnameH821ASL(145967),         -- MA562X 8POTS
-- MA562XP
					 bnameH822ASMB(145969),        -- MA562X 24POTS
					 bnameH821EPUB(145970),        -- Master board of MA562XP Box type device
					 bnameH822ASNB(145971),        -- MA562X 16POTS
-- OT929S
					 bnameH821GPMS(146044),        -- Master board of OT929S Box type device
					 bnameH821AIUG(146045),        -- 1-channel Vitual ATM Board of OT929S
					 bnameH821ETHA(146046),        -- 1-channel Vitual GE Board of OT929S
-- OFA5920
					 bnameH801GPBC(145977),         -- GPON interface board of the OFA5920. This board provides four GPON ports.
					 bnameH801SCUL(145978),         -- 200GE SCU control board of the OFA5920. This board is 300 mm deep.
					 bnameH801X2CA(145979),         -- OFA5920 board that provides two 10GE ports
					 bnameH801GICF(145980),         -- This board provides two 1000M optical ports and is used in the Frame of the R2 full-10GE switching platform.
					 bnameH801GICG(145981),         -- This board provides two 1000M electric ports and is used in the Frame of the R2 full-10GE switching platform.
					 bnameH801CITC(145982),          --Cable routing board
					 bnameH801PIUA(145983),          --Power interface board for the X/Y section of the 23-inch Frame of the NEBS

					 bnameH821MCUA(145984),         -- Control board of the MA5636
					 bnameH82XVDJ(145985),          -- 8-channel boards of the VDSL series of the MA5636
					 bnameH82XVDJA(145986),         -- 8-channel board of the VDSL series of the MA5636
					 bnameH82XVDJB(145987),         -- 8-channel board of the VDSL series of the MA5636
					 bnameH82XVDJC(145988),         -- 8-channel board of the VDSL series of the MA5636
					 bnameH82XVDJD(145989),         -- 8-channel board of the VDSL series of the MA5636
					 bnameH82XVDJE(145990),         -- 8-channel board of the VDSL series of the MA5636
					 bnameH82XVDJF(145991),         -- 8-channel board of the VDSL series of the MA5636
					 bnameH82XVDJG(145992),         -- 8-channel board of the VDSL series of the MA5636
					 bnameH82XVDJH(145993),         -- 8-channel board of the VDSL series of the MA5636
					 bnameH82XVDJI(145994),         -- 8-channel board of the VDSL series of the MA5636
					 bnameH82XVDJJ(145995),         -- 8-channel board of the VDSL series of the MA5636
					 bnameH82XVDJK(145996),         -- 8-channel board of the VDSL series of the MA5636
					 bnameH82XVDJL(145997),         -- 8-channel board of the VDSL series of the MA5636
					 bnameH82XVDJM(145998),         -- 8-channel board of the VDSL series of the MA5636
					 bnameH82XVDJN(145999),         -- 8-channel board of the VDSL series of the MA5636
					 bnameH82XVDJO(146000),         -- 8-channel board of the VDSL series of the MA5636
					 bnameH82XVDJP(146001),         -- 8-channel board of the VDSL series of the MA5636
					 bnameH82XVDJQ(146002),         -- 8-channel board of the VDSL series of the MA5636
					 bnameH82XVDJR(146003),         -- 8-channel board of the VDSL series of the MA5636
					 bnameH82XVDJS(146004),         -- 8-channel board of the VDSL series of the MA5636
					 bnameH82XVDJT(146005),         -- 8-channel board of the VDSL series of the MA5636
					 bnameH82XVDJU(146006),         -- 8-channel board of the VDSL series of the MA5636
					 bnameH82XVDJV(146007),         -- 8-channel board of the VDSL series of the MA5636
					 bnameH82XVDJW(146008),         -- 8-channel board of the VDSL series of the MA5636
					 bnameH82XVDJX(146009),         -- 8-channel board of the VDSL series of the MA5636
					 bnameH82XVDJY(146010),         -- 8-channel board of the VDSL series of the MA5636
					 bnameH82XVDJZ(146011),         -- 8-channel board of the VDSL series of the MA5636
					 bnameH801SCUB(146018),         -- Control board of the MA5600
					 bnameH801ASRB(146019),         -- Voice service board of the MA5600
					 bnameH801PMIA(146020),         -- Environment monitoring board of the MA5603
					 bnameH561SCUB(146021),         --Control board H561SCUB of the MA5600V3R3C03
					 bnameH802SHLB(146022),         -- 16-channel SHL board of the MA5600
					 bnameH801EPBA(146023),         --EPON interface board of the MA5600. This board provides four EPON ports.
					 bnameH801TOPA(146025),         -- TDM interface board of the MA5600
					 bnameH569SHEB(146026),         --Service board H569SHEB of the MA5600. This board uses the GE bus and provides 32 channels.
					 bnameH801SCUF(146027),         --Control board of the MA5600
					 bnameH802ADPD(146028),         --64-channel board of the ADSL2+ series of the MA5600
					 bnameH802ADQD(146029),         --64-channel board of the ADSL2+ series of the MA5600
					 bnameH80XASP(146030),          --64-channel voice service board of the MA5600T
					 bnameH801EDTB(146031),         --64-channel voice service board of the MA5600T
					 bnameH80xVDM (146032),         --48-channel board of the VDSL2 series of the MA5600T
					 bnameH80xVDN (146033),         --48-channel board of the VDSL2 series of the MA5600T
					 bnameH801GSCA(146034),         --GE synchronization Ethernet interface board of the MA5600T
					 bnameH801SCUN(146037),         --MA5600T control board H801SCUN
					 bnameH801X2CS(146038),         --10GE synchronized Ethernet interface board
					 bnameH802EPBD(146039),         --8EPON board
					 bnameH801PRTE(146040),         --H801PRTE Power board

					 bnameH801X4CS(146041),         --Giu board that provides 4*10GE
					 bnameH801GPBD(146042),         --8GPON board
					 bnameH801OPGA(146043),         --Ethernet access board of the MA5600. This board provides 48 FE ports.
					 bnameH801CITB(146047),         -- Environment monitoring board of the MA5603U
					 bnameH855VDMF(146048),         --48-channel board of the VDSL2 series of the MA5603U
					 bnameH801PAIB(146049),         --H801PAIB Power board
					 bnameH851VSNKE(146050),        --48-channel VDSL voice SPL board of the MA5603U
					 bnameH851VSNLE(146051),        --48-channel VDSL voice SPL board of the MA5603U
					 bnameH801GPJC(146052),        --GPON board
					 bnameH802GPBD(146054),         --8GPON board
					 bnameH801CSPA(146055),        --64-channel board of CESoP service board of the MA5600T
					 bnameH801GICK(146056),        --This board provides two 1000M optical ports and is used in the Frame of the R2 full-10GE switching platform.
					 bnameH801SPUA(146057),        --Ethernet subtend interface board of the MA5600T
					 bnameH801SPUB(146058),        --MPLS service board of the MA5600T
					 bnameH801EPBC(146059),        --EPON board
					 bnameH801BIUB(146060),         -- H801BIUB BOARD
					 bnameH801PRTG(146061),         -- H801PRTG BOARD
					 bnameH802OPGD(146062),         -- H802OPGD BOARD
					 bnameH85BVDMD(146063),         -- H85BVDMD BOARD
					 bnameH802EDTB(146064),         -- H802EDTB BOARD
					 bnameH802P2CA(146065),         -- H802P2CA BOARD
					 bnameH802OPGE(146075),         -- H802OPGE BOARD
					 bnameH801MPWE(146076),         -- Power board of MA5608T
					 bnameH808ASPB(146081),         -- H808ASPB BOARD -64-channel voice service board of the MA5600
					 bnameH801PAIC(146082),         -- H801PAIC Power board
					 bnameH803TPBA(146083),         -- 2-port 10G EPON interface board
					 bnameH803TPBC(146084),         -- 4-port 10G EPON interface board
					 bnameH805GPBD(146085),         -- 8GPON board
					 bnameH805EPBD(146086),         -- 8EPON board
					 bnameH808EPSD(146087),         -- 8EPON board
					 bnameH803GPFD(146088),         -- 16GPON board.
					 bnameH807EPBD(146089),         -- 8EPON board.
					 bnameH808EPBD(146090),         -- 8EPON board.
					 bnameH806EPFD(146091),         -- 16EPON board.
					 bnameH806GPBD(146092),         -- 8GPON board.
					 bnameH807GPBD(146093),         -- 8GPON board.
					 bnameH808GPBD(146094),         -- 8GPON board.
					 bnameH801GPFD(146095),         -- 16GPON board.
					 bnameH802GPFD(146096),         -- 16GPON board.
					 bnameH80XVPE(146097),          -- support vector board.
					 bnameH80XVCM(146098),          -- support vector board.
					 bnameH80BCVME(146099),         -- 48-channel VDSL2+ and POTS(combo) service board.
					 bnameH801XGBC(146100),         -- 4-channel 10GE GPON board.
					 bnameH801SCUH(146101),         -- two GE port and two 10GE port H801SCUH control board of MA5600T.
					 bnameH801MCUD(146102),         --  control board of MA5600T.
					 bnameH801MPWC(146103),         --  Power board of MA5600T.
					 bnameH801XEBD(146104),         --  10G EPON board of MA5600T.
					 bnameH802XGBC(146105),         --  10G EPON board of MA5600T.
					 bnameH80xVCP(146106),          --  64 VDSL Vector board of MA5600T.
					 bnameH80xVDQ(146107),          --  64 VDSL over ISDN  board of MA5600T.
					 bnameH80xVCQ(146108),          --  64 VDSL over ISDN Vector Melt board of MA5600T.
					 bnameH801GPCD(146109),         --  8GPON board of MA5600T.
					 bnameH802GPCD(146110),         --  8GPON board of MA5600T.
					 bnameH806EPCD(146111),         --  8EPON board of MA5600T.
					 bnameH809EPSD(146112),         --  8EPON board of MA5600T.
					 bnameH801EPFD(146113),         --  16EPON board of MA5600T.
					 bnameH802EPFD(146114),         --  16EPON board of MA5600T.
					 bnameH803EPFD(146115),         --  16EPON board of MA5600T.
					 bnameH801EPTD(146116),         --  16EPON board of MA5600T.
					 bnameH802EPTD(146117),         --  16EPON board of MA5600T.
					 bnameH805GPBH(146118),         --  8GPON board of MA5600T.
					 bnameH806GPBH(146119),         --  8GPON board of MA5600T.
					 bnameH807GPBH(146120),         --  8GPON board of MA5600T.
					 bnameH808GPBH(146121),         --  8GPON board of MA5600T.
					 bnameH801GPCH(146122),         --  8GPON board of MA5600T.
					 bnameH802GPCH(146123),         --  8GPON board of MA5600T.
					 bnameH801GPFH(146124),         --  16GPON board of MA5600T.
					 bnameH802GPFH(146125),         --  16GPON board of MA5600T.
					 bnameH803GPFH(146126),         --  16GPON board of MA5600T.
					 bnameH805EPBH(146127),         --  8GPON board of MA5600T.
					 bnameH806EPBH(146128),         --  8GPON board of MA5600T.
					 bnameH806EPCH(146129),         --  8GPON board of MA5600T.
					 bnameH808EPSH(146130),         --  8GPON board of MA5600T.
					 bnameH809EPSH(146131),         --  8GPON board of MA5600T.
					 bnameH801EPFH(146132),         --  16GPON board of MA5600T.
					 bnameH802EPFH(146133),         --  16GPON board of MA5600T.
					 bnameH803EPFH(146134),         --  16GPON board of MA5600T.
					 bnameH801EPTH(146135),         --  16GPON board of MA5600T.
					 bnameH802EPTH(146136),         --  16GPON board of MA5600T.
					 bnameH801XESD(146137),         --  8 ports 10G EPON board of MA5600T
					 bnameH80XVPG(146138),          --  support vector board of MA5600T.
					 bnameH806CCPE(146139),         --  64-channel POTS(combo) + Vectoring board of MA5600T.
					 bnameH801XGBD(146141),         --  8 ports 10G GPON board of MA5600T.
					 bnameH803XEBD(146142),         --  8 ports 10G EPON board of MA5600T.
					 bnameH805EPFD(146143),         --  16EPON board of MA5600T.
					 bnameH802GPMD(146144),         --  8GPON board of MA5600T.
					 bnameH805GPFD(146145),         --  16GPON board of MA5600T.
					 bnameH802XEBD(146146),         --  8 ports 10G EPON board of MA5600T.
					 bnameH802SCUN(148001),         --  MA5600T control board H802SCUN
					 bnameH801SPUH(148002),         --  interface board of the MA5600T
					 bnameH801SCUK(148003),         --  MA5600T control board H801SCUK
					 bnameH801SCUE(148004),         --  MA5600T control board H801SCUE
					 bnameH801MCUD1(148005),        --  control board of MA5608T
					 bnameH801MCUE(148006),         --  control board of MA5608T
					 bnameH801GPMD(148007),         --  8GPON board of MA5600T.
					 bnameH801SCUV(148008),         --  control board of MA5600T
					 bnameH802SCUH(148009),         --  control board of MA5600T
					 bnameH802SCUV(148010),         --  control board of MA5600T
					 bnameH802SCUB(148011),         --  control board of MA5600T

--MA5800:
					 bnameH901MPLA(148501),         --  control board of MA5800
					 bnameH901MPLB(148502),         --  control board of MA5800

					 bnameH901XGHD(148521),         --  8*10G GPON board of MA5800
					 bnameH901GPHF(148522),         --  16*GPON board of MA5800
					 bnameH901OGHK(148523),         --  48 P2P board of MA5800
					 bnameH901NXED(148524),         --  8*10GE board of MA5800
					 bnameH901OXHD(148525),         --  8*10GE extend board of MA5800
					 bnameH901PILA(148526),         --  Power board of MA5800
					 bnameH901CIUA(148527),         --  GPIO board of MA5800

--WA5700:
					 bnameBWAMPU(155648),            -- Control board MPU of the BWA indoor unit
					 bnameBWAODU(155649),            -- BWA ODU service board

--MA561X
					 bnameH838ASRB(155650),          --32-channel POTS Board of MA561X.
					 bnameH831PAIA(155651),          --Power board H831PAIA of the MA561X
					 bnameH831PDIA(155652),          --Power board H831PDIA of the MA561X

-- MA5610
					 bnameH831CCUA(155653),          -- Master board of MA5610 Box type device
					 bnameH831EIUA(155654),          -- 16 channel LAN Board of MA5610

--MA5616
					 bnameH83XVDG(155655),           --16-channel board of the VDSL series of the MA5616
					 bnameH83XADL(155656),           --32-channel board of the ADSL series of the MA5616
					 bnameH831CCUB(155657),          -- Master board of MA5616 Box type device

--MA5652
					 bnameH822GVKG(155658),          --8L VDSL2(IFX,30a),GPON(no RF)  Over ISDN
					 bnameH822GVHG(155659),          --16L VDSL2(IFX,30a),GPON(no RF)  Over ISDN
					 bnameH831EPUA(155660),          -- Master board of MA5652 Box type device

--MA561X
					 bnameH838ASPB(155661),          --64-channel POTS Board of MA561X

--MA5618
					 bnameH831CCUH(155662),
					 bnameH831PDIH(155663),
					 bnameH831PSUH(155664),
					 bnameH835ADMD(155665),
					 bnameH831VSNKE(155666),

--MA561X
					 bnameH831PAIB(155667),          --Power board H831PAIB of the MA561X

--MA5652
					 bnameH822RVKG(155668),          --8L VDSL2(IFX,30a),GPON(RF)  Over ISDN
					 bnameH822FVKG(155669),          --8L VDSL2(IFX,30a),GE(no RF)  Over ISDN
					 bnameH822RVHG(155670),          --16L VDSL2(IFX,30a),GPON(RF)  Over ISDN
					 bnameH822FVHG(155671),          --16L VDSL2(IFX,30a),GE(no RF)  Over ISDN
					 bnameH822RVJG(155672),          --8L VDSL2(IFX,30a),GPON(RF)  Over POTS
					 bnameH822GVJG(155673),          --8L VDSL2(IFX,30a),GPON(no RF) ,Over POTS
					 bnameH822FVJG(155674),          --8L VDSL2(IFX,30a),GE(no RF) ,Over POTS
					 bnameH822RVGG(155675),          --16L VDSL2(IFX,30a),GPON(RF) ,Over POTS
					 bnameH822GVGG(155676),          --16L VDSL2(IFX,30a),GPON(no RF) ,Over POTS
					 bnameH822FVGG(155677),          --16L VDSL2(IFX,30a),GE(no RF) ,Over POTS
					 bnameH821GRVAA(155713),         --24L VDSL2(IFX,17a),GPON(RF) ,Over POTS
					 bnameH821GRVAB(155715),         --24L VDSL2(IFX,17a),GPON(RF) ,Over POTS

--MA5612 +-
					 bnameH831CCFE(155678),          -- Master board of MA5612 Box type device
					 bnameH831EPFB(155679),          -- 8-channel Vitual FE Board of MA5612
					 bnameH831EIUC(155680),          -- 8-channel FE Board of MA5612
					 bnameH831ASNB(155681),          -- 16-channel Vitual POTS Board of MA5612
					 bnameH848ASNB(155682),          -- 16-channel POTS Board of MA5612

--MA5616
					 bnameH83XVDS(155683),           -- 24-channel 17a vdsl2 Over POTS Board of MA5616
					 bnameH83XVDT(155684),           -- 24-channel 17a vdsl2 Over ISDN Board of MA5616

--MA5652G
					 bnameH831ASTB(155685),         -- 4-channel POTS Board of MA5652G
--OT930
					 bnameH831CCEK(155690),          -- Master board of OT930 Box type device
					 bnameH831EPFE(155691),          -- 4-channel Vitual FE Board of OT930
					 bnameH831EDVA(155692),          -- 8-channel Vitual E1 Board of OT930
--MA5616
					 bnameH832SHLH(155693),          -- 16   G.shdsl ports G.SHDSL board
					 bnameH832DSLD(155694),          -- 8    bra ports ISDN board
--MA5662
					 bnameH825BVMD(155695),          -- Master board of MA5662 Box type device
					 bnameH825VDMD(155696),          -- 48-channel VDSL2  board for MA5662
--MA562XP
					 bnameH848ASLB(155697),          -- MA562XP 8POTS

					 bnameH831CCIK(155698),          -- Master board of ATN930 Box type device

--ATN931
					 bnameH831CCEL(155699),          -- Master board of ATN931 Box type device
					 bnameH835BVJA(155700),          -- adsl board of ATN931 Box type device
					 bnameTNC1PIU(155701),           -- power board of ATN931 Box type device

-- SD5103
					 bnameH822EPUB(155702),        -- Master board of MA562X(SD5103) Box type device
					 bnameH831CCUC(155703),        -- Master board of MA5616(SD5103) Box type device
					 bnameH832CCFE(155704),        -- Master board of MA5612(SD5103) Box type device

					 bnameH835CALE(155705),        -- 32 ADSL+32 POTS combo board
					 bnameH831EIUD(155706),        -- 4GE(combo)+4FE board
					 bnameH831E81A(155707),        -- 8E1 board
					 bnameH831EPWA(155708),        -- POE board
					 bnameH821EPFE(155709),        -- 4GE+4FE POE board
					 bnameH831EDVB(155711),        -- 4E1 Vitual board of H822CCGH
					 bnameH822CCGJ(155712),        -- Master board of MA5628(SD5103) Box type device
--MA5616
					 bnameASP(155714),             -- 64-channel VoIP POTS service board of MA5616

--MA5631
					 bnameH831CCUN(155716),        -- Master board of MA5631(SD5103) Box type device
					 bnameH831HE1A(155717),        -- 1 port EoC board of MA5631(SD5103)

--MA5628
					 bnameH822CCGJA(155718),       -- Master board of MA5628 outdoor

--MA5616
					 bnameH83BVDSB(155800),        -- 24-channel VDSL board of MA5616
--MA5612
					 bnameH837ASMB(155801),        -- 24-channel POTS board of MA5612
--MA5616
					 bnameH83BVDMM(155802),        -- 48-channel board of the VDSL series of the MA5616
					 bnameH832PDIA(155803),        -- 2 DC input power board of MA5616
--MA5622
					 bnameHS22CCVA(155804),        -- Master board of MA5623 Box type device
					 bnameHS3BCVSE(155805),        -- 24 vdsl2 + 24 pots combo board of MA5622A
					 bnameHS3BVDSE(155806),        -- 24-channel vdsl2 board of MA5623

--MA5652
					 bnameH832EPUA(155807),        -- Master board of MA5652 Box type device
					 bnameHS22VDRE(155808),        -- 24 VDSL2 + over POTS board
					 bnameHS22VDGE(155809),        -- 16 VDSL2 + over POTS board
					 bnameHS22GRVD(155810),        -- 8  VDSL2 + over POTS + RF board
					 bnameHS22VDOE(155811),        -- 24 VDSL2 + over ISDN board
					 bnameHS22VDHE(155812),        -- 16 VDSL2 + over ISDN board
					 bnameHS22VDKE(155813),        -- 8  VDSL2 + over ISDN board

--MA5621
					 bnameH822CCIQ(155814),        -- Master board of MA5621 Box type device
					 bnameH821EPFF(155815),        -- 4-channel GE board of MA5621
					 bnameH821COME(155816),        -- 4-channel Serial board of MA5621

--MA5632
					 bnameH822CCJS(155817),         -- Master board of MA5632 Box type device.

--MA5616
					 bnameH831PAIC(155818),         -- Power board H831PAIC of the MA5616.
					 bnameH83BVDLE(155819),         -- 32-port VDSL interface board of MA5616.
					 bnameH836ADPE(155820),         -- 64-port ADSL2 interface board of MA5616.

--MA5661
					 bnameH82BCVRJ(155821),         -- Master board of MA5661 Box type device.
					 bnameHS2CCVPE(155822),         -- 64 VDSL+64 POTS combo board of MA5661.
					 bnameH821PTBA(155823),         -- Power board H821PTBA of the MA5661
					 bnameHS21WF1A(155824),         -- WIFI board HS21WF1A of the MA5661.

--MA5662
					 bnameH82BCVMM(155825),          -- Master board of MA5662(SD5103) Box type device.
					 bnameHS3BVDMM(155826),          -- 48-channel VDSL2  board for MA5662(SD5103).
--MA5669
					 bnameH822EPUD(155827),         -- 1-port autoAdpt Master board of MA5669 Box type device.
					 bnameH822UPIG(155828),         -- 2-port GE board without POE of MA5669.
					 bnameH822UPWG(155829),         -- 2-port GE board with POE of MA5669.

--POE
					 bnameHS22EPFA(155910),        -- 24 POE board of 5626
					 bnameHS22EPFB(155911),        -- 16 POE board of 5626
					 bnameHS22EPFD(155913),        -- 8  POE board of 5626

--MA5616
					 bnameH832PDVA(155914),        -- Double DC Power board H832PDVA of  the  MA5616
					 bnameH831CCUE(155912),        -- Master board of MA5616(SD5130) Box type device

--MA5621A
					 bnameHS22EPFF(155915),        -- 4 FE board of MA5621A
					 bnameHS22COMF(155916),        -- 2-channel Serial board of MA5621A
					 bnameH823CCIQ(155917),        -- Master board of MA5621A Box type device

--MA5616
					 bnameH83BCVL(155918),         -- 32 VDSL+32 POTS combo board of MA5616

--MA5623
					 bnameHS22CCVB(155920),        -- Master board of MA5622A(SD5103) Box type device

--MA5616
					 bnameH83BVCMM(155921),        -- 48 VDSL baoard, supportting for vector
					 bnameH831VPBB(155922),        -- vector control engine board

					 bnameH831CCUD(155923),        -- Master board of MA5616(SD5130) Box type device
					 bnameH831PAIBA(155924),       -- Power board H831PAIBA of the MA561X
					 bnameH825EPUB(155925),        -- Master board of MA5620/26(SD5132) Box type device
					 bnameH823EPUB(155926),        -- Master board of MA5626-8 PoE(SD5130) Box type device
					 bnameHS22EPFG(155927),        -- 8 GE board of MA5626(SD5130)
--MA5623A
					 bnameHS22CCVW(155928) ,       -- Master board of MA5623A(sd5130)device.
					 bnameHS3BVCMM(155929),        -- 48 VDSL baoard, supportting for vector
--MA5633
					 bnameH822CCKRA(155930),       -- Master board of MA5633(sd5130)device.
					 bnameHS33CDAA(155931),        -- DOCSIS virtual board of MA5633

--MA5616
					 bnameH83BVCL(155932),         -- 32 VDSL + Vectoring board of MA5616

--MA5616
					 bnameH832PDVAA(155933),        -- Double DC Power board H832PDVAA of  the  MA5616, supportting vector vp subboard

--MA5698
					 bnameHS31GC4A(155934),         -- 4GE baoard(2GE+2GE COMBO) for MA5698.
--MA5694
					 bnameH821CCIC(155935),         -- Master board of MA5694(sd5130)device.
					 bnameHS21GE4A(155936),         -- 4GE baoard for MA5694.
--MA5678
					 bnameH831CCLF(155952),         -- Master board of MA5678(sd5130)device.
					 bnameH831E41B(155938),         -- 4E1 baoard for MA5678.
					 bnameHS38ASRB(155939),         -- 32POTS baoard for MA5678.
					 bnameHS31GE4A(155940),         -- 4GE baoard for MA5678.
--MA5698
					 bnameH831CCMC(155941),         -- Master board of MA5698(sd5130)device.

--MA5616A
					 bnameH831PAVD(155919),         -- 400W AC for MA5616.
					 bnameH831PAVDA(155937),        -- 400W AC + Vector for MA5616.
--MA582X
					 bnameH825XPUB(155944),         -- Master board of MA582x(sd5133)device.

--MA5622A  R313C00
					 bnameHS3BCVSB(155945),         -- 16 VDSL+16 POTS combo board of MA5622A(SD5103).
					 bnameHS3BCVSD(155946),         --  8 VDSL+ 8 POTS combo board of MA5622A(SD5103).

--MA5652   R313C00
					 bnameH823UPVB(155947),         -- Master board of MA5652(sd5130) device.
					 bnameHS23UPVB(155948),        -- 16 VDSL + Vectoring board of MA5652(sd5130) device.

--MA5611S   R313C10
					 bnameHS26BVVS(155950),         -- 16 VDSL + Vectoring board of MA5611S FTTS device.
					 bnameH826BVVS(155951),         -- Master board of MA5611S FTTS device.

--MA5694S   R313C10 DSL DOCK
					 bnameH822CC3G(155957),          --DSL DOCK Master board of MA5694S(sd5130) device.
					 bnameHS31EPFB(155959),          --3GE port board.

--MA5821    R313C10
					 bnameHS22EPGE(155961),         -- Virtual 24GE board of the MA5821.

--MA5616    R313C10
					 bnameH836VPAA(155963),         -- VPA board for MA5616.
					 bnameH832PDNAA(155964),        -- Power board (for NLV) of the MA5616.

--MA5612    R15C10
					 bnameH831EPFF(155965),          -- 2 GE Vitual Board of MA5612

--MA5694S   R313C10 PON DOCK
					 bnameH822UPWC(155970),          --PON DOCK Master board of MA5694S(sd5130) device.
					 bnameHS22GE4A(155971),          --4GE port board.
					 bnameHS22GE3A(155984),          --3GE port board.

--MA5611S   R312C91
					 bnameH82BCVMM2(155972),       -- Master board of MA5611S-DE48 north Americal device.

--MA5611S   R313C10
					 bnameH82DVCMM(155949),         -- Master board of MA5611S-DE48(sd5130) FTTS device.
					 bnameHS2DVCMM(155962),         -- 48 VDSL + Vectoring board of MA5611S-DE48(sd5130) FTTS device.

					 bnameH822CCKRB(155973),       -- Master board of mini MA5633(sd5130) device
					 bnameHS33CDAB(155974),        -- DOCSIS virtual board of mini MA5633

--MA5616   R015C00
					 bnameH831EDTB(155975),          -- E1 board of MA5616 for CCUE and CCUD.

--MA5611S  R015C00
					 bnameH823UPVBP(155976),         -- Master board of MA5611S-AE16(sd5130) FTTS device for Oman.
					 bnameHS23UPVBP(155977),         -- 16 VDSL2 board of MA5611S-AE16(sd5130) FTTS device for Oman.
					 bnameH826BVUP(155978),          -- Master board of MA5611S-DE16(sd5130) FTTS device for BT.
					 bnameHS26BVUP(155979),          -- 16 VDSL2 board of MA5611S-DE16(sd5130) FTTS device for BT.

--MA5616  R015C10
					 bnameCCM(155982),              -- 48-channel Vectoring VDSL2 + POTS COMBO service board
					 bnameVCP(155983),              -- 64-channel Vectoring VDSL2 + SPL service board

--MA5611S  R015C10
					 bnameH82BDVJM(155966),         -- Master board of MA5611S-AE08(sd5130) FTTS device.
					 bnameHS2BDVJM(155967),         -- 8 VDSL2 board of MA5611S-AE08(sd5130) FTTS device.
					 bnameH822CCKRC(155980),        -- Master board of MA5633(sd5130) device
					 bnameHS33CDAC(155981),         -- DOCSIS virtual board of MA5633
--MA5811S  R016C00
					 bnameHS35FDEM(155968),         -- 16G.FAST+VECTOR board of MA5811S FTTS device.
					 bnameH835FDEM(155969),         -- Master board of MA5811S-DE16 FTTS device.

-- WLAN
					 bnameWA611WACA(160000),        -- Master board of WS6603(WLAN V1R2) Box type device
					 bnameWA611PAIA(160001),        -- power board of WS6603(WLAN V1R2) Box type device
					 bnameWA611PDIA(160002),        -- power board of WS6603(WLAN V1R2) Box type device
					 bnameH801WACA(160003),         -- AC service Board of WS6800/WS6803(WLAN V1R3)

--SRG  series,   frome 190001
					 bnameFWG1MPUA(190001),               -- SRG2200-4, FWF1MPUA,  Main Process Unit Board
					 bnameFWF1E5FEA(190002),              -- SRG2200-4, FWF1E5FEA, 5-Port Fast Ethernet Switch Electrical Interface Board(RJ45)
					 bnameFWF1FCONT(190003),              -- SRG2200-4, FWF1FCONT, WIFI board
					 bnameFWF1E1FE(190004),               -- SRG2200-4, FWF1E1FE,  1-Port Fast Ethernet Electrical Interface Board(RJ45)
					 bnameFWF1ADPA(190005),               -- SRG2200-4, FWF1ADPA,  ADSL2+ MIC
					 bnameFWF1F1E1(190006),               -- SRG2200-4, FWF1F1E1,  1-PORT E1 Interface Board
					 bnameFWG1F2E1(190007),               -- SRG2200-4, FWG1F2E1,  2-port E1&Fractional E1 Interface Card
					 bnameSU111GPNT(190008),              -- SRG2200-4, SU111GPN,  GPON access board
					 bnameSU11FFXS(190009),               -- SRG2200-4, SU11FFXS,  16-pots vioce board
					 bnameFWG1E1GE(190010),               -- SRG2200-4, FWG1E1GE,  1-port GE Electrical Interface Card(RJ45)
					 bnameFWG1F1SA(190011),               -- SRG2200-4, FWG1F1SA,  1-Channel Sync/Async Serial Port  Interface Card
					 bnameSU11EWFS(190012),               -- 32-pots fxs board
					 bnameSU11E4MS(190013),               -- 4-pots fxs board
					 bnameSU11E4MO(190014),               -- 4-pots fxo board
					 bnameSU11E4MM(190015),               -- 2-pots fxs + 2-pots fxo board
					 bnameSU11E2MV(190016),               -- 2-pots ve1 board
					 bnameSU11UP2A(190017),               -- PON board(3 mode)

-- UA5000 from 204800
					 bnameH601ADLF(204810),          -- 16-channel ADSL over ISDN service board. This is a full-broadband service board.
					 bnameH603CSMC2(204811),          -- 16-channel ADSL2+ and POTS combo board, with the Infineon chipset
					 bnameH603CSR(204812),           -- 32-channel ADSL2+ and POTS combo board, with the Infineon chipset
					 bnameH601TSSC(204815),          -- UA broadband and narrowband test board
					 bnameH603ADR(204816),           -- The H603ADRB board is a UA 32-channel ADSL2+ service board. It uses the Infineon inband
																--  solution and belongs to the H603ADR series.
					 bnameH602CSM(204817),           -- Board of the H602CSM series
					 bnameH612IPMB(204818),          -- New control board for the master Frame of the UA5000 for BT
					 bnameH612APSB(204819),          -- New control board for the slave Frame of the UA5000 for BT

					 bnameH602CSV(204820),           -- New boards of the CSV series for BT
					 bnameH602CSVA(204821),          -- New board of the CSV series for BT
					 bnameH602CSVB(204822),          -- New board of the CSV series for BT
					 bnameH602CSVC(204823),          -- New board of the CSV series for BT
					 bnameH602CSVD(204824),          -- New board of the CSV series for BT
					 bnameH602CSVE(204825),          -- New board of the CSV series for BT
					 bnameH602CSVF(204826),          -- New board of the CSV series for BT
					 bnameH602CSVG(204827),          -- New board of the CSV series for BT
					 bnameH602CSVH(204828),          -- New board of the CSV series for BT
					 bnameH602CSVI(204829),          -- New board of the CSV series for BT
					 bnameH602CSVJ(204830),          -- New board of the CSV series for BT
					 bnameH602CSVK(204831),          -- New board of the CSV series for BT
					 bnameH602CSVL(204832),          -- New board of the CSV series for BT
					 bnameH602CSVM(204833),          -- New board of the CSV series for BT
					 bnameH602CSVN(204834),          -- New board of the CSV series for BT
					 bnameH602CSVO(204835),          -- New board of the CSV series for BT
					 bnameH602CSVP(204836),          -- New board of the CSV series for BT
					 bnameH602CSVQ(204837),          -- New board of the CSV series for BT
					 bnameH602CSVR(204838),          -- New board of the CSV series for BT
					 bnameH602CSVS(204839),          -- New board of the CSV series for BT
					 bnameH602CSVT(204840),          -- New board of the CSV series for BT
					 bnameH602CSVU(204841),          -- New board of the CSV series for BT
					 bnameH602CSVV(204842),          -- New board of the CSV series for BT
					 bnameH602CSVW(204843),          -- New board of the CSV series for BT
					 bnameH602CSVX(204844),          -- New board of the CSV series for BT
					 bnameH602CSVY(204845),          -- New board of the CSV series for BT
					 bnameH602CSVZ(204846),          -- New board of the CSV series for BT

					 bnameH605CSR(204847),           -- 32-channel ADSL2+ broadband and narrowband combo service board

					 bnameH612SPLI(204874),           -- SPL board, which uses SCM 89C51, provides 96 relays for separating
																 -- the broadband and narrowband services, and supports only the ADSL
																 -- service when used with the CSRI board
					 bnameH612GAUA(204875),           -- New board for BT. This board supports the S+C feature.
					 bnameH612SDLB(204876),           -- 16-channel broadband service board of the SHDSL access
					 bnameH603ADRF(204877),           -- 32-channel ADSL2+Annex B series board
					 bnameH601GP1A(204878),           -- UA5000 GPON board which unites Broadband and narrowband
					 bnameH601EP1A(204879),           -- UA5000 EPON board which unites Broadband and narrowband
					 bnameH601XP1A(204880),           -- UA5000 XPON board which unites Broadband and narrowband has 5*FE Electric Ports, 4*E1 Ports, 2*GE Optical Ports, 1GE Electric Port and 1GPON Port

-- AMG
					 bnameAG03PVM(262154),           -- Control board AG03PVM
					 bnameH602PVU8(262155),          -- Active/standby E1 PVU board, that is, the low-density active/standby E1
																-- PVU board under the PVM that provides 8 E1 ports
					 bnameH602PVU4(262156),          -- Active/standby E1 PVU board, that is, the low-density active/standby E1
																-- PVU board under the PVM that provides 4 E1 ports
					 bnameH601PVMB(262157),          -- High density control board H601PVMB. This board supports master extended + slave extended.
					 bnameSDLE(262158),              -- 8-channel G.SHDSL service board
					 bnameEDT(262159),               -- 16-channel narrowband E1 interface board
					 bnameTDT(262160),               -- 16-channel narrowband T1 interface board
					 bnameH601RSUG(262161),          -- RSP and G.SHDSL integrated board (a simple integration of RSP and SDL).
																-- This board provides two G.SHDSL ports.
					 bnameH602RSUG(262162),          -- RSP and G.SHDSL combo board (RSP and G.SHDSL share a CPU).
																-- This board provides two G.SHDSL ports and one E1 port.
					 bnameH601PVMA(262163),          -- H601PVMA board, which is used in the low-density Frame and supports active/standby E1 ports
					 bnameH801PVMA(262164),          -- P300 narrow control board H801PVMA (electric interface board)
					 bnameH801PVMB(262165),          -- P300 narrow control board H801PVMB (optical interface board)
					 bnameH801HWTF2(262166),          -- P300 H801HWTF HWT interface board
					 bnameH801HWCF(262167),          -- P300 H801HWCF HWC interface board
					 bnameH801TSSA(262168),          -- P300 narrowband test board: H801TSSA
					 bnameH801ASLG(262169),          -- P300 narrowband service board: H801ASLG
					 bnameH801DSCD(262170),          -- P300 2B1Q ISDN digital service board: H801DSLD
					 bnameH801PWXA(262171),          -- P300 narrowband power board: H801PWXA
					 bnameH801SDLT(262172),          -- P300 TDM SHDSL board: H801SDLT
					 bnameH801TSSB(262173),          -- P300 test board
					 bnameH801ASCK(262174),          -- P300 ASL32 service board
					 bnameH801EDTA(262175),          -- P300 EDT interface board

					 bnameAG02PVMC(262180),          -- AG02PVMC board, which is used in the low-density Frame and provides the multi-mode optical port
					 bnameAG03PVMC(262181),          -- AG03PVMC board, which is used in the high-density Frame and provides the multi-mode optical port
					 bnameH601PVMBB(262182),         -- H601PVMBB board (2.0KM), which is used in the high-density Frame and provides the optical port
					 bnameH601PVMBF(262183),         -- H601PVMBF board (15.0KM), which is used in the high-density Frame and provides the optical port
					 bnameH601PVMBG(262184),         -- H601PVMBG board (40.0KM), which is used in the high-density Frame and provides the optical port

					 bnameH612PVMB(262185),          -- High-density control board H612PVMB, which supports master extended + slave extended

					 bnameH612HWCF(262186),          -- BT H612HWCF  HWC transfer board
					 bnameH612HWTF(262187),          -- BT H612HWTF  HWT transfer board
					 bnameH612HWFF(262188),          -- BT H612HWTF  HWF transfer board
					 bnameH612PSTF(262189),          --BT H612PSTF board: HW transfer board of the small-capacity Frame H612HABF
					 bnameH612HLSF(262190),          -- BT H612HLSF transfer board
					 bnameH612HLAF(262191),          -- BT H612HLAF transfer board
					 bnameH612HLEF(262192),          -- BT H612HLEF transfer board
					 bnameH612SLTF(262193),          -- BT H612SLTF transfer board
					 bnameH612EFTF(262194),          -- BT H612EFTF transfer board
					 bnameH612E1TF(262195),          -- BT H612E1TF transfer board
					 bnameH612TSTF(262196),          -- BT H612TSTF transfer board

					 bnameH602PWX(262197),           -- Narrowband power board with the CPU

					 bnameH612PVMBG(262198),         -- H612PVMBG board (40.0KM), which is used in the high-density Frame and provides the optical port
					 bnameH612PWXB(262199),          -- BT H612PWXB power board

					 bnameH612RATF(262200),          -- BT H612RATF transfer board
					 bnameH612SLPF(262201),          -- BT H612SLPF transfer board
					 bnameH612WATF(262202),          -- BT H612WATF transfer board
					 bnameH612PRTF(262203),          -- BT H612PRTF transfer board
					 bnameH601PVMC(262204),          -- Low-density control board H601PVMC
					 bnameH601PVMCG(262205),         -- H601PVMC optical interface board, which supports the maximum transmission distance of 40.0 km
					 bnameH603RSUG(262656),          -- H603RSUG
					 bnameA04(262657),               -- A04
					 bnameA08(262658),               -- A08
					 bnameDSLD(262659),              -- 16-channel digital service board
					 bnameDSLE(262660),              -- 16-channle digital service board
					 bnameH601PVMD(262662),          -- H601PVMD
					 bnameH301HWTA(262663),          -- H301HWTA
					 bnameH602TSSB(262664),          -- H602TSSB
					 bnameCC0SASL(262665),           -- CC0SASL
					 bnameH601PVME(262669),          -- H601PVME board
					 bnameH601IPMD(262207),          -- H601IPMD board
					 bnameH612IPMD(262208),          -- H612IPMD board
					 bnameH605VDMB(262209),          -- H605VDMB board
					 bnameH603SHLB(262210),          -- H603SHLB board
					 bnameH601CPMA(262211),          -- H601CPMA board
					 bnameH601COPA(262212),          -- H601COPA board
					 bnameA64(262213),               -- A64 board
					 bnameH612PVMT(262214),          -- H612PVMT board
					 bnameGIU(262215),               -- GIU board(H612IPMD)
					 bnameH612HWCB(262216),          -- H612HWCB board
					 bnameH612HWTB(262217),          -- H612HWTB board
					 bnameH612PVMD(262218),          -- H612PVMD main board
-- 8011
					 bnameCR01LPUF(528384),             --For NE40, new main control card of NE40
					 bnameCR01CLKD(528385),             --For NE80, new main control card of NE80
					 bnameCR01NETD(528386),             --For NE80, new switch card of NE80
					 bnameCR03NETH(528387),             --For NE80, new switch card of NE80
					 bnameCR03SRUD(528388),             --For NE40-2,NE40-8,new main control card of NE40
					 bnameCR03SRUE(528389),             --For NE40-4 or NE40-8,new main control card of NE40
					 bnameCR03MPUF(528390),         --For NE80, new main control card of NE80
					 bnameCR01M2GSR(528391),            --For NE80, new power supply card of NE80
					 bnameCR01SPUA(528392),             --Flexible Card Service Processing Unit A
					 bnameCR01SPUB(528393),             --Flexible Card Service Processing Unit B, NetStream Traffic Statistics Service Board
					 bnameCR01SPUC(528394),             --Flexible Card Service Processing Unit C
					 bnameCR01CLPU(528395),             --
					 bnameCR01LPUE(528396),       --For NE40 & NE80 , mother card of NE80 and NE40
					 bnameCR01MPUE(528397),       --For NE80 , main control card of NE80
					 bnameCR01SRUC(528398),       --For NE40-2 , main control card of NE40-2
					 bnameRS01SFCB(528399),         --For S8016 SPECIAL, SWITCH CARD
					 bnameCR01NETSTREAMB(528400),         --For ne40&ne80, netstream board

-- 8031:

					 bnameCX00UNBD(536832),                   -- Unknown board
					 bnameCX21SCUB(536833),                   -- Switching and Control Processing Unit - 24 Port Fast Ethernet Electrical Interface
					 bnameCX21SCUC(536834),                   -- General Switch Control Unit-24 Ports 100BASE-FX Interface Card(SFP)
					 bnameCX31E2GE0(536835),                  -- 2 Ports 1000Base-T Gigabit Ethernet Electrical Interface Card
					 bnameCX31E2GF0(536836),                  -- 2 Ports Gigabit Ethernet SFP Optical Interface Card  With LC Connector
					 bnameCX31E2GFE0(536837),                 -- 2 Ports Gigabit Ethernet SFP Optical Interface Card With LC Connector (Enhance Board)
					 bnameCX31E4GE0(536838),                  -- 4 Ports 1000Base-T Gigabit Ethernet Electrical Interface Card
					 bnameCX31E4GF0(536839),                  -- 4 Ports Gigabit Ethernet SFP Optical Interface Card  With LC Connector
					 bnameCX31EGFE0(536840),                  -- 16 Ports Fast Ethernet Electrical Interface Card
					 bnameCX31EGFF0(536841),                  -- 16 Ports Fast Ethernet SFP Optical Interface Card With LC Connector
					 bnameCX31R2GF0(536842),                  -- 2 Ports Gigabit Ethernet RPR-SFP Optical Interface Card With LC Connector
					 bnameCX31SCUA0(536843),                  -- 48G Switching and Control Processing Unit
					 bnameCX31SCUB0(536844),                  -- 24G Switching and Control Processing Unit
					 bnameCX21FMCB(536845),                   -- CX200B Fan Monitor Control Board
					 bnameCX31FMCBA(536846),                  -- CX300A Fan Monitor Control Board
					 bnameCX31FMCBB(536847),                  -- CX300B Fan Monitor Control Board
					 bnameCX21POWDC(536848),                  -- CX200B DC Power Monitor Control Board
					 bnameCX31POWDC(536849),                  -- CX300A/B DC Power Monitor Control Board
					 bnameCX21POWAC(536850),                  -- CX200B AC Power Monitor Control Board
					 bnameCX31POWAC(536851),                  -- CX300A/B AC Power Monitor Control Board
					 bnameCX31R2UF0(536852),                  -- 2-Port STM-16c/OC-48c RPR Interface Card(SFP)
					 bnameCX31E4GFF(536853),                  -- 4-Port 1000BASE-X Interface Card(Enhanced II,SFP)
					 bnameCX31E2GFF(536854),                  -- 2-Port 1000BASE-X Interface Card(Enhanced II,SFP)
					 bnameCX31MPUA(536855),                   -- CX380 Main Processing Unit
					 bnameCX31LPUA(536856),                   -- CX380 Switch Forward Unit
					 bnameCX31E1XE(536857),                   -- CX380 1-Port 10GE Electrical Interface Card(RJ45)
					 bnameCX31E8GE(536858),                   -- CX380 8-Port 1000BASE-T Interface Card(RJ45)
					 bnameCX31EAGE(536859),                   -- CX380 10-Port 1000BASE-T Interface Card(RJ45)
					 bnameCX31ECGE(536860),                   -- CX380 12-Port 1000BASE-T Interface Card(RJ45)
					 bnameCX31EGGE(536861),                   -- CX380 16-Port 1000BASE-T Interface Card(RJ45)
					 bnameCX31E1XF(536862),                   -- CX380 1-Port 10GE Optical Interface Card(XFP)
					 bnameCX31E8GF(536863),                   -- CX380 8-Port 1000BASE-X Interface Card(SFP)
					 bnameCX31EAGF(536864),                   -- CX380 10-Port 1000BASE-X Interface Card(SFP)
					 bnameCX31ECGF(536865),                   -- CX380 12-Port 1000BASE-X Interface Card(SFP)
					 bnameCX31EGGF(536866),                   -- CX380 16-Port 1000BASE-X Interface Card(SFP)
					 bnameCX3B1AUAC(536867),                  -- CX380 Chassis(8U,2 MCU Slots,2 SRU Slots,8 SIC Slots,2 Power Supply Slots,Without MCU and Power Module)
					 bnameCX31AGE1B(536868),                  -- CX380 16-Port ATM Service E1 75ohm Interface Card
					 bnameCX31AGE1A(536869),                  -- CX380 16-Port ATM Service E1 120ohm Interface Card
					 bnameCX31AGT1(536870),                   -- CX380 16-Port ATM Service T1 100ohm Interface Card
					 bnameCX31A1CC(536871),                   -- CX380 1-Port Channelized STM-1 ATM Service Interface Card
					 bnameCX31A4CC(536872),                   -- CX380 4-Port Channelized STM-1 ATM Service Interface Card
					 bnameCX31CMPB(536873),                   -- CX380 CPU ATM Service Pinch Board
					 bnameCX31CLKA(536874),                   -- CX380 CX31MPUA Clock Pinch Board
					 bnameCX31TCMA(536875),                   -- CX380 CX31SFUA TCAM Pinch Board
					 bnameCX31BAKE(536876),                   -- CX380 Backplane

					 bnameCX61SRUA0(536877),                  -- CX600-8 - Main Process Switch Fabric Unit
					 bnameCX61MPUB0(536878),                  -- CX600-16 Main Processing Unit
					 bnameCX61SFUD0(536879),                  -- CX600-8 Switch Fabric Unit
					 bnameCX61SFUF0(536880),                  -- CX600-16 Switch Fabric Unit
					 bnameCX61FCBA(536881),                   -- CX600 Fan module
					 bnameCX61TSUA(536882),                   -- CX600 TSU Module
					 bnameCX61SPUB(536883),                   -- CX600 NETSTREAM Module
					 bnameCX61LPUA(536884),                   -- CX600 LPUA Module
					 bnameCX61LPUG(536885),                   -- CX600 LPUG Module

					 bnameCX31R2GFT(536886),                  -- 2-Port 1000BASE-X RPR Interface Card (Timing)
					 bnameCX31E2GFET(536887),                 -- 2-Port 1000BASE-X Interface Card (Timing, Enhanced I)
					 bnameCX31T8CE1A(536888),                 -- 8-Port,Channelized E1,TDM,DB68,75ohm,Interface Card
					 bnameCX31T8CE1B(536889),                 -- 8-Port,Channelized E1,TDM,DB68,120ohm,Interface Card
					 bnameCX31T8CT1(536890),                  -- 8-Port,Channelized T1,TDM,DB68,100ohm,Interface Card

					 bnameCX21SCUD(536891),                   -- General Switch Control,2GE(SFP)+16FE(SFP)+8FE(RJ45) Mixed Interface Card

					 bnameCX31T4CE1A(536892),                 -- 4-Port,Channelized E1,TDM,DB68,75ohm,Interface Card
					 bnameCX31T4CE1B(536893),                 -- 4-Port,Channelized E1,TDM,DB68,120ohm,Interface Card
					 bnameCX31T4CT1(536894),                  -- 4-Port,Channelized T1,TDM,DB68,100ohm,Interface Card
					 bnameCX31T1CCE1(536895),                 -- CX,CX31T1CC,Channelized STM-1 TDMPWE Interface Card

					 bnameCX3E1FBXA(536896),                  -- CX380 CX3E1FBXA CX380 Upper FAN Box
					 bnameCX3E1FBXB(536897),                  -- CX380 CX3E1FBXB CX380 Under FAN Box

					 bnameCX22EOFE(536898),                   -- CX200D, 24FE(RJ45)+2GE(SFP) Mixed Interface Card
					 bnameCX61LPUF(536899),                   -- CX600 LPUF Module
					 bnameCX61LPUK(536900),                   -- CX600 LPUK Module

					 bnameCX21SCUBVD(536901),                 -- Switching and Control Processing Unit - 24 Ports Fast Ethernet Electrical Interface and 1 Port MEth Interface
					 bnameCX21SCUCVC(536902),                 -- General Switch Control Unit-24 Ports 100BASE-FX Interface Card(SFP) and 1 Port MEth Interface


					 bnameCX31TMCE1A(536903),                 -- CX,CX31TMCE1A,32-Port,Channelized E1,FB,75ohm,Interface Card,1*1
					 bnameCX31TMCE1B(536904),                 -- CX,CX31TMCE1B,32-Port,Channelized E1,FB,120ohm,Interface Card,1*1
					 bnameCX31TGCE1A(536905),                 -- CX,CX31TGCE1A,16-Port,Channelized E1,FB,75ohm,Interface Card
					 bnameCX31TGCE1B(536906),                 -- CX,CX31TGCE1B,16-Port,Channelized E1,FB,120ohm,Interface Card,1*1
					 bnameCX31A4CF(536907),                   -- CX,CX31A4CF,4-Port,STM-1,SFP,Interface Card,1*1
					 bnameCX31A1KF(536908),                   -- CX,CX31A4CF,1-Port,STM-4,SFP,Interface Card,1*1

					 bnameCX31PWRAC(536909),                      -- CX380 CX31PWRAC AC Power
					 bnameCX31PWRDC(536910),                      -- CX380 CX31PWRDC DC Power
					 bnameCX31CLOCKA(536911),                     -- CX380,CX31CLKA,Stratum 3 Clock Unit
					 bnameCX31E4GFS(536912),                      -- CX380,CX31E4GFS,4-Port 1000BASE-X Optical Interface Card(SyncE,SFP)
					 bnameCX31E4GFP(536913),                      -- CX380,CX31E4GFP,4-Port 1000BASE-X Optical Interface Card(SyncE,PTP,SFP)
					 bnameCX31E4GES(536914),                      -- CX380,CX31E4GES,4-Port 1000BASE-T Interface Card(SyncE,RJ45)
					 bnameCX31E4GEP(536915),                      -- CX380,CX31E4GEP,4-Port 1000BASE-T Interface Card(SyncE,PTP,RJ45)
					 bnameCX31EGGFTA(536916),                     -- CX380,CX31EGGFTA,16-Port 1000BASE-X Interface Card(Timing transmit,SFP)
					 bnameCX31E8PA(536917),                       -- CX380,CX31E8PA,CX31EGGFTA Ethernet Pinch Board
					 bnameCX31EGGFS(536918),                      -- CX380,CX31EGGFS,16-Port 1000BASE-X Interface Card(SyncE,SFP
					 bnameCX31EGGES(536919),                      -- CX380,CX31EGGES,16-Port 1000BASE-T Interface Card(SyncE,RJ45)
					 bnameCX31LPUB(536920),                       -- CX380,CX31LPUB,Line Processing Unit
					 bnameCX31E1XFS(536921),                      -- CX380,CX31E1XFS,1-Port 10GE Optical Interface Card(SyncE,XFP)

					 bnameCX22EOFEC(536922),          -- CX200DMC, 24FE(RJ45)+2GE(SFP)+2Monitor Mixed Interface Card
					 bnameCX22EOFEA(536923),          -- CX200DEA, 24FE(RJ45)+2GE(SFP)+2Combo Mixed Interface Card
					 bnameCX22EOFEAMC(536924),        -- CX200DEAMC, 24FE(RJ45)+2GE(SFP)+2Combo+2Monitor Mixed Interface Card

					 bnameCX22EFFF(536925),           -- CX22EFFF,24FE(RJ45)+2GE(SFP)+2Combo Mixed Interface Card
					 bnameCX22EMFEA(536926),                  -- CX22EMFEA,48FE(RJ45)+4GE(SFP) Interface Card
					 bnameCX22EMFEB(536927),                  -- CX22EMFEB,24FE(RJ45)+24FE(SFP)+4GE(SFP) Interface Card
					 bnameCX22EMFF(536928),                   -- CX22EMFF,48FE(SFP)+4GE(SFP) Interface Card
					 bnameCX61LPUK1(536929),               -- CX600 CR52LPUK1,Flexible Card Line Processing Unit(LPUF-20,2 sub-slots,Not hot pluggable for sub cards) B
					 bnameCX61LPUK2(536930),               -- CX600 CR52LPUK2,Flexible Card Line Processing Unit(LPUF-21) A
					 bnameCX61LPUK3(536931),               -- CX600 CR52LPUK3,Flexible Card Line Processing Unit(LPUF-21) B
					 bnameCX61SFUG(536932),                -- CX600,CX61SFUG0,Switch Fabric Unit G

					 bnameCX22E8FF(536933),                 -- CX22E8FF,8FE(RJ45)+1Combo Mixed Interface Card
					 bnameCX22EDFE(536934),                  -- CX22EDFF,16FE(RJ45)+2Combo Mixed Interface Card
					 bnameCX22EFFE(536935),                  -- CX22EFFF,24FE(RJ45)+2Combo Mixed Interface Card
					 bnameCX61MPUD(536936),                -- CX600-3 Main Processing Unit

					 bnameCX22EFGE(536937),                  -- CX22EFGE,24GE(RJ45)+ E2XX(XGE) + E4GF(SFP) Interface Card
					 bnameCX22EFGF(536938),                  -- CX22EFGF,24GE(SFP)+ E2XX(XGE)+ E4GF(SFP)  Interface Card
					 bnameCX22EMGE(536939),                  -- CX22EMGE,48GE(RJ45)+ E2XX(XGE)+ E4GF(SFP)  Interface Card

					 bnameCX22EFGEA(536940),                  -- CX22EMGE,48GE(RJ45)+ E2XX(XGE)+ E4GF(SFP)  Interface Card
					 bnameCX22EMGEA(536941),                  -- CX22EFGEA,20GE+4COMBO General Switch Control Card
					 bnameCX22EFGEF(536942),                  -- CX22EFGEF,20GE+4COMBO,24 PORT PSE General Switch Control Card
					 bnameCX22EMGEB(536943),                  -- CX22EMGEB,44GE+4COMBO,48 PORT PSE General Switch Control Card
					 bnameCX22EFGEC(536944),                  -- CX22EFGEC,20GE+4COMBO+2XGE General Switch Control Card
					 bnameCX22EMGEC(536945),                  -- CX22EMGEC,48GE+2XGE General Switch Control Card
					 bnameCX22EFGED(536946),                  -- CX22EFGED,20GE+4COMBO+2XGE,24 PORT PSE General Switch Control Card
					 bnameCX22EMGED(536947),                  -- CX22EMGED,48GE+2XGE,48 PORT PSE General Switch Control Card
					 bnameCX22EFGEE(536948),                  -- CX22EFGEE,24GE+2*10GE General Switch Control Card(PSE)
					 bnameCX22EMGEE(536949),                  -- CX22EMGEE,48GE+2*10GE General Switch Control Card(PSE)
					 bnameCX22E8FEC(536950),                  -- CX22E8FEC,8FE+1GE General Switch Control Card(PSE)
					 bnameCX22EFFEA(536951),                  -- CX22EFFEA,24FE+2GE General Switch Control Card(PSE)
					 bnameCX22EFFEC(536952),                  -- CX22EFFEC,24FE+4GE General Switch Control Card(PSE)
					 bnameCX22EMFEC(536953),                  -- CX22EMFEC,48FE+4GE General Switch Control Card(PSE)

					 bnameCX22LS31T28SA(536954),               -- CX22LS31T28SA,24GE+2GE COMBO+2GE(SFP) General Switch Control Card
					 bnameCX22LS31T18SA(536955),               -- CX22LS31T18SA,16GE+2GE(SFP)General Switch Control Card
					 bnameCX22LS51T24C(536956),               -- CX22LS51T24C,24GE + 4GE(SFP) Interface Card
					 bnameCX22LS51S24C(536957),               -- CX22LS51S24C,24GE(SFP) + 4GE(SFP)Interface Card
					 bnameCX22LS51T6UM(536958),               -- CX22LS51T6UM,4GE+2GE COMBO General Switch Control Card(PSE)
					 bnameCX22LS31T24C(536959),               -- CX22LS31T24C,24FE+2GE(SFP) Interface Card
					 bnameCX22LS51S24CA(536960),               -- CX22LS51S24CA,24GE + 4GE(SFP) General Switch Control Card(PSE)

					 bnameCX62NPUI20(536961),                  -- CX600-16 Main Processing Unit
					 bnameCX62NPU20B0(536962),                  -- CX600-16 Main Processing Unit
					 bnameCX62MPUB4(536963),                  -- CX600-8 - Main Process Switch Fabric Unit
					 bnameCX62SFU40B0(536964),                  -- CX600-16 Main Processing Unit
					 bnameCX62SRU40A4(536965),                  -- CX600-8 - Main Process Switch Fabric Unit
					 bnameCX62SFU40C0(536966),                  -- CX600-16 Main Processing Unit
					 bnameCX62MPUD0(536967),                  -- CX600-16 Main Processing Unit
					 bnameCX62ISUF10(536968),                  -- CX600-8 - Main Process Switch Fabric Unit
					 bnameCX62ISUF20(536969),                  -- CX600-16 Main Processing Unit
					 bnameCX62ISUF40(536970),                  -- CX600-8 - Main Process Switch Fabric Unit
					 bnameCX62MPUG0(536971),                  -- CX600-8 - Main Process Switch Fabric Unit
					 bnameLS61S24N(536972),                   -- CX22LS61S24N,24*10G(SFP+) General Switch Control Card(PSE)
					 bnameLS61S48N(536973),                   -- CX22LS61S48N,48*10G(SFP+) General Switch Control Card(PSE)
					 bnameLS61S48NA(536974),                  -- CX22LS61S48N,48*10G(SFP+) General Switch Control Card(PSE)
					 bnameLS52T28S(536975),               -- S5700 LS52T28S 24-Port GE RJ45+4-Port GE SFP General Switch Control Card 1*1  S5728P-LI
					 bnameLS52V28S(536976),            -- S5700 LS52V28S 24-Port GE RJ45+4-Port GE SFP General Switch Control Card PSE 1*1 S5728P-PWR-LI
					 bnameLS52T52S(536977),              -- S5700 LS52T28S 48-Port GE RJ45+4-Port GE SFP General Switch Control Card 1*1 S5752P-LI
					 bnameLS52V52S(536978),           -- S5700 LS52V28S 48-Port GE RJ45+4-Port GE SFP General Switch Control Card (PSE)1*1  S5752P-PWR-LI
					 bnameLS52T28C(536979),              -- S5700 LS52T28C 24-Port GE RJ45+4-Port 10GE SFP+ General Switch Control Card 1*1  S5728X-EI
					 bnameLS52T52C(536980),              -- S5700 LS52T52C 48-Port GE RJ45+4-Port 10GE SFP+ General Switch Control Card 1*1 S5752X-EI
					 bnameLS52T28SS5328PLI(536981),              -- S5300 LS52T28S 24-Port GE RJ45+4-Port GE SFP General Switch Control Card 1*1  S5328P-LI
					 bnameLS52T52SS5352PLI(536982),              -- S5300 LS52T28S 48-Port GE RJ45+4-Port GE SFP General Switch Control Card 1*1 S5352P-LI
					 bnameLS52T28SB(536983),               -- S5700 LS52T28S 24-Port GE RJ45+4-Port GE SFP General Switch Control Card 1*1  S5728P-LI-DC
					 bnameLS52T52SB(536984),              -- S5700 LS52T28S 48-Port GE RJ45+4-Port GE SFP General Switch Control Card 1*1 S5752P-LI-DC
					 bnameLS52T28SC(536985),              -- S5300 LS52T28S 24-Port GE RJ45+4-Port GE SFP General Switch Control Card 1*1  S5328P-LI-DC
					 bnameLS52T52SC(536986),              -- S5300 LS52T28S 48-Port GE RJ45+4-Port GE SFP General Switch Control Card 1*1 S5352P-LI-DC
					 bnameLS52T28SD(536987),              -- S5700 LS52T28S 24-Port GE RJ45+4-Port GE SFP General Switch Control Card 1*1  S5700S-28P-LI-AC
					 bnameLS52T52SD(536988),              -- S5700 LS52T52S 48-Port GE RJ45+4-Port GE SFP General Switch Control Card 1*1 S5700S-52P-LI-AC
					 bnameLS52V28C(536989),              -- S5700 LS52V28C 24-Port GE RJ45+4-Port 10GE SFP+ General Switch Control Card 1*1  S5710-28C-PWR-EI
					 bnameLS52V52C(536990),              -- S5700 LS52V52C 48-Port GE RJ45+4-Port 10GE SFP+ General Switch Control Card 1*1  S5710-52C-PWR-EI
					 bnameCX61MPUH(536991),                -- CX600-X3 Main Processing Unit
					 bnameCX62SFU100D(536992),             -- CX600-X8 Switch Fabric Unit
					 bnameCX62SRU100D(536993),             -- CX600-X8 Main Process Switch Fabric Unit

					 bnameCX68MPUK(536994),                -- CX600-X2 Main Processing Unit,
					 bnameCX68NPU50(536995),               -- CX600-X2 Net  Processing Unit,
					 bnameCX68NPU50B(536996),              -- CX600-X2 Net  Processing Unit outside,
					 bnameCX68PSUC(536997),                -- CX600-X2 DC/DC Power Module,
					 bnameCX68FAN(536998),                 -- CX600-X2 FAN Module,
					 bnameCX68E8GEB(536999),               -- 100M/1000M interface card (RJ45),
					 bnameCX68L2XFB(537000),               -- 2x10G  card,
					 bnameCX68TIE1(537001),                -- 32E1 interface card,
					 bnameCX68C4CF(537002),                -- 4*155M CPOS interface card
					 bnameES5D2T10M000(537003),            -- S5700 ES5D2T10M000 8 GE RJ45,2 GE SFP,AC 110/220V S5700-10P-LI-AC
					 bnameES5D2V10M000(537004),            -- S5700 ES5D2V10M000 8 GE RJ45,2 GE SFP,AC 110/220V S5700-10P-PWR-LI-AC
					 bnameES5D2H26S000(537005),            -- S5700 ES5D2H26S000 12-Prot GE RJ45 + 12-Port GE Optical + 2-Port SFP+ Optical General Switch Control Unit S5700-26X-SI-12S-AC
					 bnameES5D2T28S000(537006),            -- S5700 ES5D2T28S000 24 GE RJ45,4 10GE SFP+,AC 110/220V S5700-28X-LI-AC
					 bnameES5D2T28S000S5728XLIDC(537007),  -- S5700 ES5D2T28S000 24 GE RJ45,4 10GE SFP+,DC -48V S5700-28X-LI-DC
					 bnameES5D2T52S000(537008),            -- S5700 ES5D2T52S000 48 GE RJ45,4 10GE SFP+,AC 110/220V S5700-52X-LI-AC
					 bnameES5D2T52S000S5752XLIDC(537009),  -- S5700 ES5D2T52S000 48 GE RJ45,4 10GE SFP+,DC -48V S5700-52X-LI-DC
					 bnameES5D2V28S000(537010),            -- S5700 ES5D2V28S000 24 GE RJ45,4 10GE SFP+,PoE,AC 110/220V S5700-28X-PWR-LI-AC
					 bnameES5D2V52S000(537011),            -- S5700 ES5D2V52S000 48 GE RJ45,4 10GE SFP+,PoE,AC 110/220V S5700-52X-PWR-LI-AC
					 bnameS5710108CPWRHIAC(537012),        -- S5710 ES5D2T10M000 48 GE RJ45,8 10GE SFP+,PoE,Four Slots of Flexible Card,Dual Slots of Power,Including Dual 580W AC PowerS5710-108C-PWR-HI-AC
					 bnameS5710108CHIAC(537013),           -- S5710 ES5D2T56S000 48-Port GE RJ45 + 8-Port 10GE SFP+ Optical General Switch Control Unit S5710-108C-HI-AC
					 bnameS6300E6000(537014),              -- S5700 S6300_E6000  20-Port 10GE SFP+ Optical General Switch Control Unit E6000
					 bnameS5310PLIAC(537015),           -- S5300-10P-LI-AC
					 bnameS531028CEI(537016),           -- S5310-28C-EI 20-port GE RJ45+4-port Combo + 4-Port SFP+ Optical General Switch Control Unit
					 bnameS531052CEI(537017),           -- S5310-52C-EI 48-Port GE RJ45 + 4-Port SFP+ Optical General Switch Control Unit
					 bnameS2328PEIAC(537018),           -- 24-port FE RJ45 + 4-port SFP General Switch Control Unit
					 bnameS275026TPPWREIAC(537019),     -- S2750-26TP-PWR-EI-AC Mainframe(24 FE RJ45,2 GE COMBO,PoE,AC 110/220V)
					 bnameS235026TPPWREIAC(537020),     -- S2350-26TP-PWR-EI-AC Mainframe(24 FE RJ45,2 GE COMBO,PoE,AC 110/220V)
					 bnameS275126TPPWREIAC(537021),     -- S2751-26TP-PWR-EI-AC Mainframe(24FE RJ45,2 GE COMBO,8 PoE,AC 110/220V)
					 bnameS235028TPEIAC(537022),        -- S2350-28TP-EI-AC Mainframe(24 FE RJ45,2 GE Combo,2 GE SFP,AC 110/220V)
					 bnameS275028TPEIAC(537023),        -- S2750-28TP-EI-AC Mainframe(24 FE RJ45,2 GE Combo,2 GE SFP,AC 110/220V)
					 bnameS235018TPPWREIAC(537024),     -- S2350-18TP-PWR-EI-AC Mainframe(16 FE RJ45,2 GE COMBO,PoE,AC 110/220V)
					 bnameS275018TPPWREIAC(537025),     -- S2750-18TP-PWR-EI-AC Mainframe(16 FE RJ45,2 GE COMBO,PoE,AC 110/220V)
					 bnameS330052PEI(537026),           -- S3300-52P-EI Mainframe( 48FE + 4 GE SFP)
					 bname8031S5700-28X-LI-24S-DC(537027),    --S5700-28X-LI-24S-DC Mainframe(20 GE SFP,4 GE Combo,4 10GE SFP+,DC -48V)
					 bname8031S5300-28X-LI-24S-DC(537028),    --S5300-28X-LI-24S-DC Mainframe(20 GE SFP,4 GE Combo,4 10GE SFP+,DC -48V)
					 bname8031S5700-28X-LI-24S-AC(537029),    --S5700-28X-LI-24S-AC Mainframe(20 GE SFP,4 GE Combo,4 10GE SFP+,AC 110/220V)
					 bname8031S5300-28X-LI-24S-AC(537030),   --S5300-28X-LI-24S-AC Mainframe(20 GE SFP,4 GE Combo,4 10GE SFP+,AC 110/220V)
					 bname8031S5300-28X-LI-DC(537031),      --5300-28X-LI-DC Mainframe(24 GE RJ45,4 10GE SFP+,DC -48V)
					 bname8031S5300-28X-LI-AC(537032),      --S5300-28X-LI-AC Mainframe(24 GE RJ45,4 10GE SFP+,AC 110/220V)
					 bname8031S2750-28TP-PWR-EI-AC(537033),  --S2750-28TP-PWR-EI-AC Mainframe(24 FE RJ45,2 GE SFP,2 GE COMBO,PoE,AC 110/220V)
					 bname8031S2350-28TP-PWR-EI-AC(537034),  --S2350-28TP-PWR-EI-AC  Mainframe(24 FE RJ45,2 GE SFP,2 GE COMBO,PoE,AC 110/220V)
					 bname8031S2751-28TP-PWR-EI-AC(537035),  --S2751-28TP-PWR-EI-AC  Mainframe(24FE RJ45,2 GE SFP,2 GE COMBO,12 PoE,AC 110/220V)
					 bname8031S2350-20TP-PWR-EI-AC(537036),   --S2350-20TP-PWR-EI-AC Mainframe(16 FE RJ45,2 GE SFP,2 GE COMBO,PoE,AC 110/220V)
					 bname8031S2750-20TP-PWR-EI-AC(537037),   --S2750-20TP-PWR-EI-AC Mainframe(16 FE RJ45,2 GE SFP,2 GE COMBO,PoE,AC 110/220V)
					 bname8031S2350-28TP-EI-AC(537038),     --S2350-28TP-EI-AC Mainframe(24 FE RJ45,2 GE SFP,2 GE COMBO,AC 110/220V)
					 bname8031S2750-28TP-EI-AC(537039),   --S2750-28TP-EI-AC  Mainframe(24 FE RJ45,2 GE SFP,2 GE COMBO,AC 110/220V)
					 bname8031S3700-28TP-EI-24S-DC(537040), -- S3700-28TP-EI-24S-DC

					 bname8031S5701-28X-LI-AC(537041),           --S5701-28X-LI-AC       Metro Service Platform for V2R3C00
					 bname8031S5701-28X-LI-24S-AC(537042),       --S5701-28X-LI-24S-AC   Metro Service Platform for V2R3C00
					 bname8031S5700-28P-LI-BAT(537043),          --S5700-28P-LI-BAT      Metro Service Platform for V2R3C02
					 bname8031S5700-28P-LI-4AH(537044),          --S5700-28P-LI-4AH      Metro Service Platform for V2R3C02
					 bname8031S5700-28P-LI-24S-BAT(537045),      --S5700-28P-LI-24S-BAT  Metro Service Platform for V2R3C02
					 bname8031S5700-28P-LI-24S-4AH(537046),      --S5700-28P-LI-24S-4AH  Metro Service Platform for V2R3C02
					 bname8031S5300-28P-LI-BAT(537047),          --S5300-28P-LI-BAT      Metro Service Platform for V2R3C02
					 bname8031S5300-28P-LI-4AH(537048),          --S5300-28P-LI-4AH      Metro Service Platform for V2R3C02
					 bname8031S5300-28P-LI-24S-BAT(537049),      --S5300-28P-LI-24S-BAT  Metro Service Platform for V2R3C02
					 bname8031S5300-28P-LI-24S-4AH(537050),      --S5300-28P-LI-24S-4AH  Metro Service Platform for V2R3C02
					 bname8031S5700-28X-LI-24CS-AC(537051),      --S5700-28X-LI-24CS-AC  Metro Service Platform for V2R3C02
					 bname8031S5700-28X-LI-24CS-DC(537052),      --S5700-28X-LI-24CS-DC  Metro Service Platform for V2R3C02
					 bname8031S5300-28X-LI-24CS-AC(537053),      --S5300-28X-LI-24CS-AC  Metro Service Platform for V2R3C02
					 bname8031S5300-28X-LI-24CS-DC(537054),      --S5300-28X-LI-24CS-DC  Metro Service Platform for V2R3C02

					 bname8031S5310-108C-PWR-HI(537055),         --S5310-108C-PWR-HI     Metro Service Platform for V2R5C00
					 bname8031S5300-10P-PWR-LI-AC(537056),       --S5300-10P-PWR-LI-AC   Metro Service Platform for V2R5C00
					 bname8031S5300-28P-PWR-LI-AC(537057),       --S5300-28P-PWR-LI-AC   Metro Service Platform for V2R5C00
					 bname8031S5300-52P-PWR-LI-AC(537058),       --S5300-52P-PWR-LI-AC   Metro Service Platform for V2R5C00
					 bname8031S5300-52X-LI-AC(537059),           --S5300-52X-LI-AC       Metro Service Platform for V2R5C00
					 bname8031S5300-52X-LI-DC(537060),           --S5300-52X-LI-DC       Metro Service Platform for V2R5C00
					 bname8031S5300-28X-PWR-LI-AC(537061),       --S5300-28X-PWR-LI-AC   Metro Service Platform for V2R5C00
					 bname8031S5300-52X-PWR-LI-AC(537062),       --S5300-52X-PWR-LI-AC   Metro Service Platform for V2R5C00
					 bname8031S2350-28TP-EI-DC(537063),          --S2350-28TP-EI-DC      Metro Service Platform for V2R5C00
					 bname8031S5700-28TP-LI-AC(537064),          --S5700-28TP-LI-AC      Metro Service Platform for V2R3C10
					 bname8031S5700-28TP-PWR-LI-AC(537065),      --S5700-28TP-PWR-LI-AC  Metro Service Platform for V2R3C10
					 bname8031S5701-28TP-PWR-LI-AC(537066),      --S5701-28TP-PWR-LI-AC  Metro Service Platform for V2R3C10

					 bname8031S5720-56C-HI-AC(537067),           --S5720-56C-HI-AC       Metro Service Platform for V2R6C00
					 bname8031S5720-56C-PWR-HI-AC(537068),       --S5720-56C-PWR-HI-AC   Metro Service Platform for V2R6C00
					 bname8031S5720-32C-HI-24S-AC(537069),       --S5720-32C-HI-24S-AC   Metro Service Platform for V2R6C00

					 bname8031S1720-28GFR-4TP(537070),           --S1720-28GFR-4TP       Metro Service Platform for V2R6C10
					 bname8031S1720-20GFR-4TP(537071),           --S1720-20GFR-4TP       Metro Service Platform for V2R6C10
					 bname8031S2720-28TP-EI-AC(537072),          --S2720-28TP-EI-AC      Metro Service Platform for V2R6C10

					 bname8031S5720-36C-EI-28S-AC(537073),       --S5720-36C-EI-28S-AC   Metro Service Platform for V2R7C00
					 bname8031S5320-36C-EI-28S-AC(537074),       --S5320-36C-EI-28S-AC   Metro Service Platform for V2R7C00
					 bname8031S5320-36C-EI-28S-DC(537075),       --S5320-36C-EI-28S-DC   Metro Service Platform for V2R7C00
					 bname8031S5720-56C-EI-48S-AC(537076),       --S5720-56C-EI-48S-AC   Metro Service Platform for V2R7C00
					 bname8031S5320-56C-EI-48S-AC(537077),       --S5320-56C-EI-48S-AC   Metro Service Platform for V2R7C00
					 bname8031S5320-56C-EI-48S-DC(537078),       --S5320-56C-EI-48S-DC   Metro Service Platform for V2R7C00
					 bname8031S5720-36C-EI-AC(537079),           --S5720-36C-EI-AC       Metro Service Platform for V2R7C00
					 bname8031S5320-36C-EI-AC(537080),           --S5320-36C-EI-AC       Metro Service Platform for V2R7C00
					 bname8031S5320-36C-EI-DC(537081),           --S5320-36C-EI-DC       Metro Service Platform for V2R7C00
					 bname8031S5720-36PC-EI-AC(537082),          --S5720-36PC-EI-AC      Metro Service Platform for V2R7C00
					 bname8031S5320-36PC-EI-AC(537083),          --S5320-36PC-EI-AC      Metro Service Platform for V2R7C00
					 bname8031S5320-36PC-EI-DC(537084),          --S5320-36PC-EI-DC      Metro Service Platform for V2R7C00
					 bname8031S5720-56C-EI-AC(537085),           --S5720-56C-EI-AC       Metro Service Platform for V2R7C00
					 bname8031S5320-56C-EI-AC(537086),           --S5320-56C-EI-AC       Metro Service Platform for V2R7C00
					 bname8031S5320-56C-EI-DC(537087),           --S5320-56C-EI-DC       Metro Service Platform for V2R7C00
					 bname8031S5720-56PC-EI-AC(537088),          --S5720-56PC-EI-AC      Metro Service Platform for V2R7C00
					 bname8031S5320-56PC-EI-AC(537089),          --S5320-56PC-EI-AC      Metro Service Platform for V2R7C00
					 bname8031S5320-56PC-EI-DC(537090),          --S5320-56PC-EI-DC      Metro Service Platform for V2R7C00
					 bname8031S5720-36C-PWR-EI-AC(537091),       --S5720-36C-PWR-EI-AC   Metro Service Platform for V2R7C00
					 bname8031S5320-36C-PWR-EI-AC(537092),       --S5320-36C-PWR-EI-AC   Metro Service Platform for V2R7C00
					 bname8031S5320-36C-PWR-EI-DC(537093),       --S5320-36C-PWR-EI-DC   Metro Service Platform for V2R7C00
					 bname8031S5720-56C-PWR-EI-AC(537094),       --S5720-56C-PWR-EI-AC   Metro Service Platform for V2R7C00
					 bname8031S5320-56C-PWR-EI-AC(537095),       --S5320-56C-PWR-EI-AC   Metro Service Platform for V2R7C00
					 bname8031S5720-56C-PWR-EI-AC1(537096),      --S5720-56C-PWR-EI-AC1  Metro Service Platform for V2R7C00
					 bname8031S5720-32X-EI-24S-AC(537097),       --S5720-32X-EI-24S-AC   Metro Service Platform for V2R7C00
					 bname8031S5320-32X-EI-24S-AC(537098),       --S5320-32X-EI-24S-AC   Metro Service Platform for V2R7C00
					 bname8031S5320-32X-EI-24S-DC(537099),       --S5320-32X-EI-24S-DC   Metro Service Platform for V2R7C00
					 bname8031S5720-50X-EI-46S-AC(537100),       --S5720-50X-EI-46S-AC   Metro Service Platform for V2R7C00
					 bname8031S5320-50X-EI-46S-AC(537101),       --S5320-50X-EI-46S-AC   Metro Service Platform for V2R7C00
					 bname8031S5320-50X-EI-46S-DC(537102),       --S5320-50X-EI-46S-DC   Metro Service Platform for V2R7C00
					 bname8031S5720-32X-EI-AC(537103),           --S5720-32X-EI-AC       Metro Service Platform for V2R7C00
					 bname8031S5320-32X-EI-AC(537104),           --S5320-32X-EI-AC       Metro Service Platform for V2R7C00
					 bname8031S5320-32X-EI-DC(537105),           --S5320-32X-EI-DC       Metro Service Platform for V2R7C00
					 bname8031S5720-32P-EI-AC(537106),           --S5720-32P-EI-AC       Metro Service Platform for V2R7C00
					 bname8031S5320-32P-EI-AC(537107),           --S5320-32P-EI-AC       Metro Service Platform for V2R7C00
					 bname8031S5320-32P-EI-DC(537108),           --S5320-32P-EI-DC       Metro Service Platform for V2R7C00
					 bname8031S5720-52X-EI-AC(537109),           --S5720-52X-EI-AC       Metro Service Platform for V2R7C00
					 bname8031S5320-52X-EI-AC(537110),           --S5320-52X-EI-AC       Metro Service Platform for V2R7C00
					 bname8031S5320-52X-EI-DC(537111),           --S5320-52X-EI-DC       Metro Service Platform for V2R7C00
					 bname8031S5720-52P-EI-AC(537112),           --S5720-52P-EI-AC       Metro Service Platform for V2R7C00
					 bname8031S5320-52P-EI-AC(537113),           --S5320-52P-EI-AC       Metro Service Platform for V2R7C00
					 bname8031S5320-52P-EI-DC(537114),           --S5320-52P-EI-DC       Metro Service Platform for V2R7C00
					 bname8031S5720-50X-EI-AC(537115),           --S5720-50X-EI-AC       Metro Service Platform for V2R7C00
					 bname8031S5320-50X-EI-AC(537116),           --S5320-50X-EI-AC       Metro Service Platform for V2R7C00
					 bname8031S5320-50X-EI-DC(537117),           --S5320-50X-EI-DC       Metro Service Platform for V2R7C00




-- 8090:
					 bname8090DEVUNKNOWN(561152),         -- Unknown board type
					 bname8090DEVMPU(561153),             -- Main Processing Unit
					 bname8090DEVSFU(561154),             -- Switch Fabric Unit for Full Capacity System
					 bname8090DEVLPU(561155),             -- Flexible Card Line Processing Unit,obsolete
					 bname8090DEVCLK(561156),             -- system clk board on MPU board,obsolete
					 bname8090DEVPOWER(561157),           -- DC/DC Power Module
					 bname8090DEVFAN(561158),             -- Fan Module
					 bname8090DEVLCD(561159),             -- LCD Module
					 bname8090DEVSRUMPU(561160),          -- MPU Module on SRU board,obsolete
					 bname8090DEVSRUSFU(561161),          -- Switch Fabric Unit for Half & Halflow Frame System for SFUD
					 bname8090DEVNETSTREAM(561162),       -- NETSTREAM Module
					 bname8090DEVRAINIER(561163),      -- RAINIER Module
					 bname8090DEVGRE(561164),              -- GRE Module
					 bname8090DEVTSU(561165),              -- TSU Module
					 bname8090DEVSFEA(561166),              -- Switch Fabric Unit for Full Capacity System
					 bname8090DEVSRU(561167),             -- SRU  board
					 bname8090DEVLPUA(561168),            -- LPUA Module
					 bname8090DEVLPUB(561169),            -- LPUB Module
					 bname8090DEVLPUC(561170),            -- LPUC Module
					 bname8090DEVCR52LPUE(561171),        -- CR52LPUE Module
					 bname8090DEVCR53LPUF(561172),        -- CR53LPUF Module
					 bname8090DEVLPUG(561173),            -- LPUG Module
					 bname8090DEVLPUH(561174),            -- LPUH Module
					 bname8090DEVLPUK(561175),            -- LPUK Module
					 bname8090DEVSPU(561176),             -- NETSTREAM Module
					 bname8090DEVSFUG(561177),            -- SFUG Module
					 bname8090DEVMPUA(561178),            -- Cluster Central Main Processing Unit A
					 bname8090DEVSFUA(561179),            -- Cluster Central Switch Fabric Unit A
					 bname8090DEVECUA(561180),            -- Cluster Electric Cross Unit A
					 bname8090DEVICUA(561181),            -- Cluster Internal Communication Unit A
					 bname8090DEVCR52LPUM(561182),        -- CR52LPUM Module
					 bname8090DEVCR52LPUI(561183),        -- CR52LPUI Module
					 bname8090DEVLPUK1(561184),           -- LPUF-20-B Module
					 bname8090DEVLPUK2(561185),           -- LPUF-21-A Module
					 bname8090DEVLPUK3(561186),           -- LPUF-21-B Module
					 bname8090DEVMPUD(561187),            -- NE40E-3 Main Processing Unit
					 bname8090DEVMPUC(561188),            -- MPUC Module,abandon
					 bname8090DEVSRU40A(561189),          -- SRU40A Module,abandon
					 bname8090DEVLPUN(561190),            -- LPUN Module
					 bname8090DEVLPUR(561191),            -- LPUR Module
					 bname8090DEVSFU40A(561192),          -- SFU40A Module
					 bname8090DEVSFU40B(561193),          -- SFU40B Module
					 bname8090DEVSFUI(561194),            -- SFUI Module
					 bname8090DEVCR56RPUA(561195),        -- RPUA Module on MPUC or SRUC (X8,X16)
					 bname8090DEVCR56MADA(561196),        -- MADA Module on MPUC(X16)
					 bname8090DEVCR57FRA40A(561197),      -- FRA40A Module on MPUC(X8)
					 bname8090DEVCR56SFUF100B(561198),      --CR56SFUF100B Module
					 bname8090DEVCR52L4XXB(561199),       -- 4-Port 10GBase LAN/WAN-XFP Integrated  Line Processing Unit (LPUI-40)
					 bname8090DEVCR52EKGFB(561200),       -- 40-Port 100/1000Base-X-SFP Integrated Line Processing Unit(LPUI-40)
					 bname8090DEVCR52EKGFC(561201),       -- 40-Port 100/1000Base-X-SFP Switch Line Processing Unit(LPUS-20)
					 bname8090DEVCR52EKGEB(561202),       -- 40-Port 10/100/1000Base-RJ45 Switch Line Processing Unit(LPUS-20)
					 bname8090DEVCR52L4XXC(561203),       -- 4-Port 10GBase LAN/WAN-XFP Switch Line Processing Unit(LPUS-20)
					 bname8090DEVCR55SFUI100A(561204),    -- CR55SFUI100A Module
					 bname8090DEVCR55ECU100A(561205),     -- CR55ECU100A Module
					 bname8090DEVCR52SFEB(561206),        -- Switch Fabric Unit for Full Capacity System (FE600)
					 bname8090DEVCR52LPUF40B(561207),     -- CR5MLPUF402B(SBOM),Flexible Card Line Processing Unit(LPUF-40,2 sub-slots) B
					 bname8090DEVCR52LPUF40A(561208),     -- CR5MLPUF402A(SBOM),Flexible Card Line Processing Unit(LPUF-40,2 sub-slots) A (L3VPN, MVPN, IPv6 Enhanced)

					 bname8090DEVCR57FRA100A(561209),      -- FRA100A Module on MPUC(X8)
					 bname8090DEVCR57FRA200A(561210),      -- FRA200A Module on MPUC(X8)

					 bname8090DEVCR57LPUF41A(561211),     -- LPUF41A 40G LPU,SD58X2 Solution ,MIPS CPU
					 bname8090DEVCR57LPUF101A(561212),    -- Double LPUF41A, 100G LPU

					 bname8090DEVCR57SRU100A(561213),     -- Two piece 8890, 100G SFU, used with X8 SRUA100A MPU
					 bname8090DEVCR57SRU200A(561214),     -- Two piece 5802, 200G SFU, used with X8 SRUA200A MPU

					 bname8090DEVCR57SFU100C(561215),     -- Two piece 8890, X8 100G SFU
					 bname8090DEVCR57SFU200B(561216),     -- Two piece 5802, X16 100G-200G SFU
					 bname8090DEVCR57SFU200C(561217),     -- Two piece 5802, X8 100G-200G SFU
					 bname8090DEVCR55MPUAB(561218),       -- CCC Main Processing Unit
					 bname8090DEVCR56LPUF100B(561219),    -- NE5000E Line Processing Unit(NE5000E LPUF-100)
					 bname8090DEVCR56SFUF100C(561220),    -- NetEngine5000E,CR56SFUF100C, 100G Switch Fabric Unit B(SFUF-100-C)
					 bname8090DEVCR56SFU200A(561221),     -- NetEngine5000E,CR56SFU200A, 200G Switch Fabric Unit B(SFU-200-A)
					 bname8090DEVCR52LPUR(561225),        -- NetEngine5000E,CR52EKGFY0,40-Port 1000Base-X-SFP Line Processing Unit
					 bname8090DEVCR52SPUC(561226),        -- NetEngine5000E,CR52SPUC0, Versatile Service Process Unit C
					 bname8090DEVCR56LPUF200A(561227),    -- NE5000E Line Processing Unit(NE5000E LPUF-200)
					 bname8090DEVMPUH(561228),            -- NE40E-X3-NEW Main Processing Unit
					 bname8090DEVCR57SFU100D(561229),     -- one piece 5802, X8 100G SFU
					 bname8090DEVCR57SRU100D(561230),     -- one piece 5802, 100G SFU, used with X8 SRUA100A MPU
					 bname8090DEVPMU(561231),             -- NE5000E PMU Unit

					 bnameNECXMEDEVHBOARD(565000),        --any MPU,SFU and LPU's MIB value in NE,CX,and ME for CCB result.{8090 : 0x00089000 ~ 0x00089fff }



-- ME60:
					 bnameME60UNKNOWN(159744),
					 bnameME60MPUA(159745),                -- ME60-16 MPU Module
					 bnameME60MPUB(159746),                -- ME60-8 MPU Module
					 bnameME60SFUA(159747),                -- ME60-16 SFU Module
					 bnameME60SFUB(159748),                -- ME60-8 SFU Module
					 bnameME60CLK(159749),                 -- CLK Module
					 bnameME60POWER(159750),               -- POWER Module
					 bnameME60FAN(159751),                 -- FAN Module
					 bnameME60LCD(159752),                 -- LCD Module
					 bnameME60CR52LPUA(159753),            -- CR52LPUA Module
					 bnameME60ME01LPUA(159754),            -- ME01LPUA Module
					 bnameME60ME01TSUA0(159755),            --CR52TSU Module
					 bnameME60ME01SSUA0(159756),            --CR52SSU Module
					 bnameME60ME01SBCA0(159757),            --CR52SBC Module
					 bnameME60ME01VSUA0TSU(159758),         --ME01TSU Module
					 bnameME60ME01VSUA0SSU(159759),         --ME01SSU Module
					 bnameME60ME01VSUA0SBC(159760),         --ME01SBC Module
					 bnameME60ME01LPUE(159761),             --LPUE Module
					 bnameME60RAINIER(159762),              --RAINIER Module

					 bnameME60ME01VSUA0DPI(159763),         --ME01DPI Module
					 bnameME60ME01LPUB0(159764),        --Ezchip LPUB Module
					 bnameME60ME01LPUC0(159765),         --Ezchip LPUC Module

					 bnameME60MPUC(159766),                 --ME60-16 MPU Module
					 bnameME60SFUC(159767),                 --ME60-16 SFU Module
					 bnameME60SFUD(159768),                  --ME60-16 SFU Module

-- S9300:       0x000A1000~0x000A1fff(659456~663551)
					 bnameLE01SRUA(659456),                   --Switching and Routing Unit Board
					 bnameLE01G48SA(659457),                  --48-Port 100/1000BASE-X Interface Card(EA,SFP)
					 bnameLE01G24SA(659458),                  --E-product,LE01G24S,24Gig-Ethernet SFP Interface Board,1*1
					 bnameLE01G48SE(659459),
					 bnameLE01G48SC(659460),                  --48-Port 100/1000BASE-X Interface Card(EC,SFP)
					 bnameLE01G48SD(659461),                  --48-Port 100/1000BASE-X Interface Card(ED,SFP)
					 bnameLE01POWER(659462),                  --Quidway S9300,LE02CMUA,Centralized Monitoring Board,1*2
					 bnameLE01FAN(659463),                    --Metro Ethernet E Product,LE02FCMA,Fan Monitor and Control Board,1*3
					 bnameLE0MSRUA(659464),                   --Quidway S9300,LE02SRUA,Switch and Routing Unit(256G Switch Capacity),1*1
					 bnameLE0D00SRUB00(659465),                    --Main Control Unit
					 bnameLE0MMCUA(659466),                   --Main Control Unit
					 bnameLE0DCMUA0000(659467),
					 bnameLE0MG48TC(659468),                  --Quidway S9300,LE02G48TC,48-Port 1000BASE-T Interface Card(EC,RJ45),128K MAC,1*1
					 bnameLE02G48VC(659469),
					 bnameLE0MX4UXC(659470),                  --E-product,LE02X4UXC,40G Ethernet XFP Interface Board,1*1
					 bnameLE0MX2UXC(659471),                  --E-product,LE02X2UXC,20G Ethernet XFP Interface Board,1*1
					 bnameLE0D0S24XC00(659472),
					 bnameLE02T24XC(659473),
					 bnameLE02V24XC(659474),
					 bnameLE0MG48SC(659475),                  --Quidway S9300,LE02G48SC,48-Port 1000BASE-X Interface Card(EC,SFP),128K MAC,1*1
					 bnameLE0MG24SC(659476),                  --24-Port 100/1000BASE-X Interface Card(EC,SFP)
					 bnameLE02G24TC(659477),
					 bnameLE0MG48TD(659478),                  --Quidway S9300-LE02G48TD-48-Port 1000BASE-T Interface Card-512K MAC-1*1
					 bnameLE02G48VD(659479),
					 bnameLE0DX4UXED00(659480),
					 bnameLE02X2UXD(659481),
					 bnameLE02S24XD(659482),
					 bnameLE02T24XD(659483),
					 bnameLE02V24XD(659484),
					 bnameLE0MG48SD(659485),                  --48-Port 1000BASE-X Interface
					 bnameLE0MG24SD(659486),                  --24-Port 100/1000BASE-X Interface Card(ED,SFP)
					 bnameLE0MG48SA(659487),                  --Quidway S9300,LE02G48SA,48-Port 1000BASE-X Interface Card(EA,SFP),32K MAC,1*1
					 bnameLE0MG48TA(659488),                  --Quidway S9300,LE02G48TA,48-Port 1000BASE-T Interface Card(EA,RJ45),32K MAC,1*1
					 bnameLE02G48VA(659489),
					 bnameLE0MX4UXA(659490),                  --4-Port 10GBASE-X Interface Card(EA,XFP)
					 bnameLE0MX2UXA(659491),                  --2-Port 10GBASE-X Interface Card(EA,XFP)
					 bnameLE0DS24XEA00(659492),                  --24-Port 100/1000BASE-X and 2-Port 10GBASE-X Interface Card(EA,SFP/XFP)
					 bnameLE0DT24XEA00(659493),                  --24-Port 100/1000BASE-T and 2-Port 10GBASE-X Interface Card(EA,RJ45/XFP)
					 bnameLE02V24XA(659494),
					 bnameLE0MG24SA(659495),                  --Quidway S9300,LE02G24SA,24-Port 1000BASE-X Interface Card(SI,SFP),32K MAC,1*1
					 bnameLE02G24TA(659496),
					 bnameLE0MG24CA(659497),                  --Quidway S9300,LE02G24CA,24-Port 1000BASE-X and 8-Port 1000BASE-T Combo Interface Card(SI,SFP/RJ45),1*1
					 bnameLE0DX12XSA00(659498),                  --12-Port 10GBASE-X Interface Card(SA,SFP+)
					 bnameLE02E4UAA(659499),
					 bnameLE0D0E12GA00(659500),                  --12-Port EPON Interface and 12-Port 1000BASE-X Interface Card (SFP)
					 bnameLE02X2NXA(659501),                  --2-Port 10GBASE-X NP Interface Card(NP,XFP)
					 bnameLE02G24NA(659502),                  --24-Port 1000BASE-X NP Interface Card(NP,SFP)
					 bnameLE01G48SB(659503),
					 bnameLE01MCUA(659504),                  --Main Control Unit
					 bnameLE0D00SRUB00VB(659505),                --LE02SRUB_VB
					 bnameLE0MSRUAVB(659506),                --LE02SRUA_VB
					 bnameLE0MF48SA(659507),                 --48-Port 100BASE-FX Interface Card(EA,SFP)
					 bnameLE0MF48SC(659508),                 --48-Port 100BASE-FX Interface Card(EC,SFP)
					 bnameLE02F48SD(659509),                 --48-Port 100BASE-FX Interface Card(ED,SFP)
					 bnameLE0MF48TA(659510),                 --48-Port 100/1000BASE-T Interface Card(EA,RJ45)
					 bnameLE0MF48TC(659511),                 --48-Port 100/1000BASE-T Interface Card(EC,RJ45)
					 bnameLE02F48TD(659512),                 --48-Port 100/1000BASE-T Interface Card(ED,RJ45)
					 bnameLE02T24SA(659513),                 --24-Port 100/1000BASE-T and 8-Port 100/1000BASE-X Interface Card(EA,RJ45/SFP)
					 bnameLE0DSRUA(659514),                  --Main Control Unit(BITS/1588)
					 bnameLE0DMCUA(659515),                  --Main Control Unit(BITS/1588)
					 bnameLE0D0VAMPA00(659516), --Valude-added Services Unit
					 bnameLE02G48TH(659517),
					 bnameLE0DG48VEA00(659518),
					 bnameLE0D0WMNPA00(659519),  --WAN Interface Services Process Unit
					 bnameLE0DG48CEAT0(659520), --12-port 100/1000BASE-X and 36-port 100/1000BASE-T Interface Card (32K MAC)
					 bnameLE0DF48TFA00(659521),  --48-Port 100BASE-T Interface Card(32K MAC)
					 bnameLE0DG48SFA00(659522),  --48-Port 1000BASE-T Interface Card(32K MAC)
					 bnameLE0DG48TFA00(659523),  --48-Port 1000BASE-T Interface Card(32K MAC)
					 bnameLE02X48SSA(659524),  --48-Port 10GBASE-X Interface Card
					 bnameLE02DPDA(659525),
					 bnameLE02LEDA(659526),
					 bnameLE0DG24CEAS0(659527), --24-Port 100/1000BASE-X and 8-Port 100/1000BASE-T Combo Interface Card(EA,SFP/RJ45,1588)
					 bnameLE02L4UFFC(659528),  --4-Port 40GBASE-X Interface Card(FC,CFP)
					 bnameLE0DG48TBC00(659529),  --48-Port 100/1000BASE-T Interface Card(BC,RJ45)
					 bnameLE0DG48SBC00(659530),  --48-Port 100/1000BASE-X Interface Card(BC,SFP)
					 bnameLE0DG24TFA00(659531),  --24-Port 100/1000BASE-T Interface Card(FA,RJ45)
					 bnameLE02S24XEJ(659532),  --24-Por 100/1000BASE-X and 2-Port 10GBASE-X Interface Card(EC,SFP/XFP,1588)
					 bnameLE0DX40SFC00(659533),  --40-Port 10GBASE-X Interface Card(FC,SFP+)
					 bnameLE0DX16SFC00(659534),  --16-Port 10GBASE-X Interface Card(FC,SFP+)
					 bnameLE2D2X08SED0(659535),  --8-Port 10GBASE-X Interface Card(ED,SFP+)
					 bnameLE02L8UQFC(659536),  --8-Port 40GBASE-X Interface Card(FC,QSFP+)
					 bnameLE2D2SRUDC00(659537),   --Quidway S9706/S9712,Main Control Unit D,Clock
					 bnameLE2D2MB86S00(659538),   --X86 Service Process Mother board
					 bnameLE1D2L02QFC0(659539),   --2-port 40GBASE-X interface card(FC,QSFP+)
					 bnameLE2D2L08QFC0(659540),   --8-port 40GBASE-X interface card(FC,QSFP+)
					 bnameLE2D2X08SED4(659541),   --8-Port 10GBASE-X Interface Card(ED,SFP+)
					 bnameLE2D2X16SFC1(659542),   --16-Port 10GBASE-X Interface Card(FC,SFP+) FCC
					 bnameLE2D2X40SFC1(659543),   --40-Port 10GBASE-X Interface Card(FC,SFP+) FCC
					 bnameLE2D2X08SED1(659544),   --8-Port 10GBASE-X Interface Card(ED,SFP+) FCC
					 bnameLE2D2X08SED5(659545),   --8-Port 10GBASE-X Interface Card(ED,SFP+) FCC
					 bnameLE2D2SRUDC01(659546),   --Quidway S9706/S9712,Main Control Unit D,Clock FCC
					 bnameLE1D2X12SEE0(659547),   --12-Port 10GBASE-X Interface Card(EE,SFP+)
					 bnameLE1D2X24SEE0(659548),   --24-Port 10GBASE-X Interface Card(EE,SFP+)
					 bnameLE1D2X12SED0(659549),   --12-Port 10GBASE-X Interface Card(ED,SFP+)
					 bnameLE1D2X24SED0(659550),   --24-Port 10GBASE-X Interface Card(ED,SFP+)
					 bnameLE02SRUC(659551),       --S9706/S9712,Main Control Unit C,Option clock
					 bnameLH03MCUA(659552),
					 bnameLH02SRUD0(659553),
					 bnameLH02G48TC(659554),
					 bnameLH02X4UXC(659555),
					 bnameLH02S24XC(659556),
					 bnameLH02G48SC(659557),
					 bnameLH02X4UXD(659558),
					 bnameLH02T24XA(659559),
					 bnameLH02X12SA(659560),
					 bnameLH1D2L02QFC0(659561),
					 bnameLH1D2X08SED4(659562),
					 bnameLE1D2X02XEC1(659563),      --S9300,LE1D2X02XEC1,2-Port 10GBASE-X Interface Card(EC,XFP),FCC,128K MAC-1*1
					 bnameLE1D2X04XEC1(659564),      --S9300,LE1D2X04XEC1,4-Port 10GBASE-X Interface Card(EC,XFP),FCC,128K MAC-1*1
					 bnameLE1D2G48TX1E(659565),      --S9300,48-Port 10/100/1000BASE-T Interface Card(XF,RJ45)
					 bnameLE1D2G48SX1E(659566),      --S9300,48-Port 100/1000BASE-X Interface Card(XF,SFP)
					 bnameLE1D2S04SX1E(659567),      --S9300,4-Port 10GBASE-X and 24-Port 100/1000BASE-X and 8-Port 10/100/1000BASE-T Combo Interface Card(XF,RJ45/SFP/SFP+)
					 bnameLE1D2S08SX1E(659568),      --S9300,8-Port 10GBASE-X and 8-Port 100/1000BASE-X and 8-Port 10/100/1000BASE-T Combo Interface Card(XF,RJ45/SFP/SFP+)
					 bnameLH2D2G48TX1E(659569),      --S9300E,48-Port 10/100/1000BASE-T Interface Card(XF,RJ45)
					 bnameLH2D2G48SX1E(659570),      --S9300E,48-Port 100/1000BASE-X Interface Card(XF,SFP)
					 bnameLH2D2S04SX1E(659571),      --S9300E,4-Port 10GBASE-X and 24-Port 100/1000BASE-X and 8-Port 10/100/1000BASE-T Combo Interface Card(XF,RJ45/SFP/SFP+)
					 bnameLH2D2S08SX1E(659572),      --S9300E,8-Port 10GBASE-X and 8-Port 100/1000BASE-X and 8-Port 10/100/1000BASE-T Combo Interface Card(XF,RJ45/SFP/SFP+)
					 bnameLE2D2X48SEC0(659573),      --S9300,48-Port 10GBASE-X Interface Card(ED,SFP+)
					 bnameLH2D2X48SEC0(659574),      --S9300E,48-Port 10GBASE-X Interface Card(ED,SFP+)
					 bnameLE1D2ACU2000(659575),      --S9300,ACU2
					 bnameLH2D2ACU2000(659576),      --S9300E,ACU2
					 bnameLE1D2FW00S01(659577),      --S9300/S9300E,20G Firewall Unit


-- S7700:       0x000A2000~0x000A2fff(663552~667647)
					 bnameES0D00SRUA00(663552),      --Quidway S7700,ES02SRUA,Switch and Routing Unit(256G Switch Capacity),1*1
					 bnameES0D00SRUB00(663553),      --Main Control Unit
					 bnameES0D00MCUA00(663554),      --Main Control Unit
					 bnameES0D0G24SA00(663555),      --Quidway S7700,ES02G24SA,24-Port 1000BASE-X Interface Card(SI,SFP),32K MAC,1*1
					 bnameES0D0G24SC00(663556),      --24-Port 100/1000BASE-X Interface Card(EC,SFP)
					 bnameES0D0G48TA00(663557),      --Quidway S7700,ES02G48TA,48-Port 1000BASE-T Interface Card(EA,RJ45),32K MAC,1*1
					 bnameES0D0G48TC00(663558),      --Quidway S7700,ES02G48TC,48-Port 1000BASE-T Interface Card(EC,RJ45),128K MAC,1*1
					 bnameES0D0G48VA00(663559),
					 bnameES0D0G48SA00(663560),      --Quidway S7700,ES02G48SA,48-Port 1000BASE-X Interface Card(EA,SFP),32K MAC,1*1
					 bnameES0D0G48SC00(663561),      --Quidway S7700,ES02G48SC,48-Port 1000BASE-X Interface Card(EC,SFP),128K MAC,1*1
					 bnameES0D0F48TA00(663562),      --48-Port 100/1000BASE-T Interface Card(EA,RJ45)
					 bnameES02F48SA(663563),         --48-Port 100BASE-FX Interface Card(EA,SFP)
					 bnameES0D0G24CA00(663564),      --Quidway S7700,ES02G24CA,24-Port 1000BASE-X and 8-Port 1000BASE-T Combo Interface Card(SI,SFP/RJ45),1*1
					 bnameES0D0T24XA00(663565),      --24-Port 100/1000BASE-T and 2-Port 10GBASE-X Interface Card(EA,RJ45/XFP)
					 bnameES0D0S24XA00(663566),      --24-Port 100/1000BASE-X and 2-Port 10GBASE-X Interface Card(EA,SFP/XFP)
					 bnameES0D0X4UXA00(663567),      --4-Port 10GBASE-X Interface Card(EA,XFP)
					 bnameES0D0X4UXC00(663568),      --E-product,ES02X4UXC,40G Ethernet XFP Interface Board,1*1
					 bnameES0D0X2UXA00(663569),      --2-Port 10GBASE-X Interface Card(EA,XFP)
					 bnameES0D0X2UXC00(663570),      --E-product,ES02X2UXC,20G Ethernet XFP Interface Board,1*1
					 bnameES0D0E12GA00(663571),      --12-Port EPON Interface and 12-Port 1000BASE-X Interface Card (SFP)
					 bnameES0DG48CEAT0(663572),      --12-port 100/1000BASE-X and 36-port 100/1000BASE-T Interface Card (32K MAC)
					 bnameLE0DCMUA0000S7700(663573),
					 bnameES0D00SRUA00VB(663574),    --ES02SRUA_VB
					 bnameES0D00SRUB00VB(663575),    --ES02SRUB_VB
					 bnameES03SRUA(663576),          --Main Control Unit(BITS/1588)
					 bnameES03MCUA(663577),          --Main Control Unit(BITS/1588)
					 bnameES0D0F48TC00(663578),      --48-Port 100/1000BASE-T Interface Card(EC,RJ45)
					 bnameES0DF48TFA00(663579),      --48-Port 100BASE-T Interface Card(32K MAC)
					 bnameES0DG48TFA00(663580),      --48-Port 1000BASE-T Interface Card(32K MAC)
					 bnameES0D0X12SA00(663581),
					 bnameES0DG24TFA00(663582),
					 bnameES1D2X04XED0(663583),      --4-Port 10GBASE-X Interface Card(ED,XFP)
					 bnameES1D2G48SFA0(663584),      --48-Port 100/1000BASE-X Interface Card(FA,SFP)
					 bnameES1D2G48SED0(663585),      --48-Port 100/1000BASE-X Interface Card(ED,SFP)
					 bnameES1D2X16SFC0(663586),      --16-Port 10GBASE-X Interface Card(FC,SFP+)
					 bnameES1D2X40SFC0(663587),      --40-Port 10GBASE-X Interface Card(FC,SFP+)
					 bnameES2D2MB86S00(663588),      --X86 Service Process Mother board
					 bnameES1D2L02QFC0(663589),      --2-port 40GBASE-X interface card(FC,QSFP+)
					 bnameES1D2X08SED4(663590),      --8-Port 10GBASE-X Interface Card(ED,SFP+)
					 bnameES1D2X08SED5(663591),      --8-Port 10GBASE-X Interface Card(ED,SFP+) FCC
					 bnameES1D2G24SED0(663592),      --24-Port 100/1000BASE-X Interface Card(ED,SFP)
					 bnameES1D2G48TED0(663593),      --48-Port 10/100/1000BASE-T Interface Card(ED,RJ45)
					 bnameES1D2G48SBC0(663594),      --48-Port 100/1000BASE-X Interface Card(BC,SFP)
					 bnameES1D2G48TBC0(663595),      --48-Port 10/100/1000BASE-T Interface Card(BC,RJ45)
					 bnameES1D2S24XEC0(663596),      --24-Port 100/1000BASE-X and 2-Port 10GBASE-X Interface Card(EC,SFP/XFP)
					 bnameES1D2X12SEE0(663597),      --12-Port 10GBASE-X Interface Card(EE,SFP+)
					 bnameES1D2X12SED0(663598),      --12-Port 10GBASE-X Interface Card(ED,SFP+)
					 bnameES1D2X02XEC1(663599),      --S7700,ES1D2X02XEC1,2-Port 10GBASE-X Interface Card(EC,XFP),FCC,128K MAC-1*1
					 bnameES1D2X04XEC1(663600),      --S7700,ES1D2X04XEC1,4-Port 10GBASE-X Interface Card(EC,XFP),FCC,128K MAC-1*1
					 bnameES1D2G48TX1E(663601),      --S7700,48-Port 10/100/1000BASE-T Interface Card(XF,RJ45)
					 bnameES1D2G48SX1E(663602),      --S7700,48-Port 100/1000BASE-X Interface Card(XF,SFP)
					 bnameES1D2S04SX1E(663603),      --S7700,4-Port 10GBASE-X and 24-Port 100/1000BASE-X and 8-Port 10/100/1000BASE-T Combo Interface Card(XF,RJ45/SFP/SFP+)
					 bnameES1D2S08SX1E(663604),      --S7700,8-Port 10GBASE-X and 8-Port 100/1000BASE-X and 8-Port 10/100/1000BASE-T Combo Interface Card(XF,RJ45/SFP/SFP+)
					 bnameES1D2ACU2000(663605),      --S7700,ACU2
					 bnameES1D2G48VEA2(663606),      --S7700,48-Port 10/100/1000BASE-T POE Interface Card(EA,RJ45,POE,EEE)

-- S9700:       0x000A7000~0x000A7fff(684032~688127)
					 bnameEH02MCUA(684032),            --Quidway S9703 Main Control Unit A LE02MCUA
					 bnameEH1D2MCUAC00(684033),            --Quidway S9703 Main Control Unit A,Clock LE03MCUA
					 bnameEH1D2F48TEA0(684034),           --48-Port 10/100BASE-T Interface Card(EA,RJ45)
					 bnameEH1D2F48TEC0(684035),           --48-Port 10/100BASE-T Interface Card(EC,RJ45)
					 bnameEH1D2F48TFA0(684036),          --48-Port 10/100BASE-T Interface Card(FA,RJ45)
					 bnameEH1D2F48SEA0(684037),           --48-Port 100BASE-FX Interface Card(EA,SFP)
					 bnameEH1D2F48SEC0(684038),           --48-Port 100BASE-X Interface Card(EC,SFP)
					 bnameEH1D2G24TFA0(684039),          --24-Port 10/100/1000BASE-T Interface Card(FA,RJ45)
					 bnameEH1D2G24SSA0(684040),           --24-Port 100/1000BASE-X Interface Card(SA,SFP)
					 bnameEH1D2G24SEC0(684041),           --24-Port 100/1000BASE-X Interface Card(EC,SFP)
					 bnameEH1D2G24SED0(684042),           --24-Port 100/1000BASE-X Interface Card(ED,SFP)
					 bnameEH1D2S24CSA0(684043),           --24-Port 100/1000BASE-X and 8-Port 10/100/1000BASE-T Combo Interface Card(SA,SFP/RJ45)
					 bnameEH1D2S24CEA0(684044),         --24-Port 100/1000BASE-X and 8-Port 10/100/1000BASE-T Combo Interface Card(EA,SFP/RJ45,1588)
					 bnameEH1D2G48TEA0(684045),           --48-Port 10/100/1000BASE-T Interface Card(EA,RJ45)
					 bnameEH1D2G48TEC0(684046),           --48-Port 10/100/1000BASE-T Interface Card(EC,RJ45)
					 bnameEH1D2G48TFA0(684047),          --48-Port 10/100/1000BASE-T Interface Card(FA,RJ45)
					 bnameEH1D2G48TED0(684048),           --48-Port 10/100/1000BASE-T Interface Card(ED,RJ45)
					 bnameEH1D2G48TBC0(684049),          --48-Port 10/100/1000BASE-T Interface Card(BC,RJ45)
					 bnameEH1D2G48SEA0(684050),           --48-Port 100/1000BASE-X Interface Card(EA,SFP)
					 bnameEH1D2G48SEC0(684051),           --48-Port 100/1000BASE-X Interface Card(EC,SFP)
					 bnameEH1D2G48SFA0(684052),          --48-Port 100/1000BASE-X Interface Card(FA,SFP)
					 bnameEH1D2G48SED0(684053),           --48-Port 100/1000BASE-X Interface Card(ED,SFP)
					 bnameEH1D2G48SBC0(684054),          --48-Port 100/1000BASE-X Interface Card(BC,SFP)
					 bnameEH1D2T36SEA0(684055),         --36-Port 10/100/1000BASE-T and 12-Port 100/1000BASE-X Interface Card(EA,RJ45/SFP)
					 bnameEH1D2X02XEA0(684056),           --2-Port 10GBASE-X Interface Card(EA,XFP)
					 bnameEH1D2X02XEC0(684057),           --2-Port 10GBASE-X Interface Card(EC,XFP)
					 bnameEH1D2T24XEA0(684058),           --24-Port 10/100/1000BASE-T and 2-Port 10GBASE-X Interface Card(EA,RJ45/XFP)
					 bnameEH1D2S24XEA0(684059),           --24-Port 100/1000BASE-X and 2-Port 10GBASE-X Interface Card(EA,SFP/XFP)
					 bnameEH1D2S24XEC0(684060),           --24-Port 100/1000BASE-X and 2-Port 10GBASE-X Interface Card(EC,SFP/XFP)
					 bnameEH1D2X04XEA0(684061),           --4-Port 10GBASE-X Interface Card(EA,XFP)
					 bnameEH1D2X04XEC0(684062),           --4-Port 10GBASE-X Interface Card(EC,XFP)
					 bnameEH1D2X04XED0(684063),           --4-Port 10GBASE-X Interface Card(ED,XFP)
					 bnameEH1D2X12SSA0(684064),           --12-Port 10GBASE-X Interface Card(SA,SFP+)
					 bnameEH1D2X40SFC0(684065),          --40-Port 10GBASE-X Interface Card(FC,SFP+)
					 bnameEH1D2E12GSA0(684066),           -- 12-Port EPON Interface and 12-Port 1000BASE-X Interface Card (SFP)
					 bnameEH1D200CMU00(684067),
					 bnameEH1D2SRUDC00(684068),           --Quidway S9306E/S9312E,Main Control Unit D,Clock
					 bnameEH1D2X08SED0(684069),          --8-Port 10GBASE-X Interface Card(ED,SFP+)
					 bnameEH02L8UQFC(684070),          --8-Port 40GBASE-X Interface Card(FC,QSFP+)
					 bnameEH1D2WM00000(684071),           --WAN Interface Services Process Card
					 bnameEH1D2X16SFC0(684072),          --16-Port 10GBASE-X Interface Card(FC,SFP+)
					 bnameEH2D2MB86S00(684073),            --X86 Service Process Mother board
					 bnameEH1D2L02QFC0(684074),            --2-port 40GBASE-X interface card(FC,QSFP+)
					 bnameEH2d2L08QFC0(684075),            --8-port 40GBASE-X interface card(FC,QSFP+)
					 bnameEH1D2X08SED4(684076),            --8-Port 10GBASE-X Interface Card(ED,SFP+)
					 bnameEH1D2SRUDC01(684077),            --Quidway S9306E/S9312E,Main Control Unit D,Clock FCC
					 bnameEH1D2X16SFC1(684078),            --16-Port 10GBASE-X Interface Card(FC,SFP+) FCC
					 bnameEH1D2X40SFC1(684079),           --40-Port 10GBASE-X Interface Card(FC,SFP+) FCC
					 bnameEH1D2X08SED1(684080),            --8-Port 10GBASE-X Interface Card(ED,SFP+) FCC
					 bnameEH1D2X08SED5(684081),            --8-Port 10GBASE-X Interface Card(ED,SFP+) FCC
					 bnameEH1D2X12SEE0(684082),            --12-Port 10GBASE-X Interface Card(EE,SFP+)
					 bnameEH1D2X24SEE0(684083),            --24-Port 10GBASE-X Interface Card(EE,SFP+)
					 bnameEH1D2X12SED0(684084),            --12-Port 10GBASE-X Interface Card(ED,SFP+)
					 bnameEH1D2X24SED0(684085),            --24-Port 10GBASE-X Interface Card(ED,SFP+)
					 bnameEH1D2SRUC000(684086),            --S9706/S9712,Main Control Unit C,Option clock
					 bnameEH1D2X02XEC1(684087),            --S9700,EH1D2X02XEC1,2-Port 10GBASE-X Interface Card(EC,XFP),FCC,128K MAC-1*1
					 bnameEH1D2X04XEC1(684088),            --S9700,EH1D2X04XEC1,4-Port 10GBASE-X Interface Card(EC,XFP),FCC,128K MAC-1*1
					 bnameEH1D2G48TX1E(684089),            --S9700,48-Port 10/100/1000BASE-T Interface Card(XF,RJ45)
					 bnameEH1D2G48SX1E(684090),            --S9700,48-Port 100/1000BASE-X Interface Card(XF,SFP)
					 bnameEH1D2S04SX1E(684091),            --S9700,4-Port 10GBASE-X and 24-Port 100/1000BASE-X and 8-Port 10/100/1000BASE-T Combo Interface Card(XF,RJ45/SFP/SFP+)
					 bnameEH1D2S08SX1E(684092),            --S9700,8-Port 10GBASE-X and 8-Port 100/1000BASE-X and 8-Port 10/100/1000BASE-T Combo Interface Card(XF,RJ45/SFP/SFP+)
					 bnameEH1D2X48SEC0(684093),            --S9700,48-Port 10GBASE-X Interface Card(ED,SFP+)
					 bnameEH1D2ACU2000(684094),            --S9700,ACU2


-- S12700:       0x000AB000~0x000ABfff(700416~704511)

					 bnameET1D2G48TEA0(700416),            --S12700,48-Port 10/100/1000BASE-T Interface Card(EA,RJ45)
					 bnameET1D2G48TEC0(700417),            --S12700,48-Port 10/100/1000BASE-T Interface Card(EC,RJ45)
					 bnameET1D2G48TED0(700418),            --S12700,48-Port 10/100/1000BASE-T Interface Card(ED,RJ45)
					 bnameET1D2G48TX1E(700419),            --S12700,48-Port 10/100/1000BASE-T Interface Card(XF,RJ45)
					 bnameET1D2G24SEC0(700420),            --S12700,24-Port 100/1000BASE-X Interface Card(EC,SFP)
					 bnameET1D2G24SED0(700421),            --S12700,24-Port 100/1000BASE-X Interface Card(ED,SFP)
					 bnameET1D2G48SEA0(700422),            --S12700,48-Port 100/1000BASE-X Interface Card(FA,SFP)
					 bnameET1D2G48SEC0(700423),            --S12700,48-Port 100/1000BASE-X Interface Card(EC,SFP)
					 bnameET1D2G48SED0(700424),            --S12700,48-Port 100/1000BASE-X Interface Card(ED,SFP)
					 bnameET1D2G48SX1E(700425),            --S12700,48-Port 100/1000BASE-X Interface Card(XF,SFP)
					 bnameET1D2X04XEA0(700426),            --S12700,4-Port 10GBASE-X Interface Card(FA,XFP)
					 bnameET1D2X04XEC1(700427),            --S12700,4-Port 10GBASE-X Interface Card(EC,XFP)
					 bnameET1D2X04XED0(700428),            --S12700,4-Port 10GBASE-X Interface Card(ED,XFP)
					 bnameET1D2X08SED5(700429),            --S12700,8-Port 10GBASE-X Interface Card(ED,SFP+)
					 bnameET1D2X12SSA0(700430),            --S12700,12-Port 10GBASE-X Interface Card(FA,SFP+)
					 bnameET1D2X16SSC0(700431),            --S12700,16-Port 10GBASE-X Interface Card(FC,SFP+)
					 bnameET1D2X40SFC0(700432),            --S12700,40-Port 10GBASE-X Interface Card(FC,SFP+)
					 bnameET1D2X48SEC0(700433),            --S12700,48-Port 10GBASE-X Interface Card(EC,SFP+)
					 bnameET1D2L02QSC0(700434),            --S12700,2-port 40GBASE-X interface card(FC,QSFP+)
					 bnameET1D2L08QSC0(700435),            --S12700,8-port 40GBASE-X interface card(FC,QSFP+)
					 bnameET1D2T24XFA0(700436),            --S12700,24-Port 10/100/1000BASE-T and 2-Port 10GBASE-X Interface Card (FA,RJ45/XFP)
					 bnameET1D2S24XFA0(700437),            --S12700,24-Port 100/1000BASE-X and 2-Port 10GBASE-X Interface Card(EA,SFP/XFP)
					 bnameET1D2S24XEC0(700438),            --S12700,24-Port 100/1000BASE-X and 2-Port 10GBASE-X Interface Card(EC,SFP/XFP)
					 bnameET1D2T36SEA0(700439),            --S12700,36-Port 10/100/1000BASE-T and 12-Port 100/1000BASE-X Interface Card(FA,RJ45/SFP)
					 bnameET1D2S04SX1E(700440),            --S12700,4-Port 10GBASE-X and 24-Port 100/1000BASE-X and 8-Port 10/100/1000BASE-T Combo Interface Card(XF,RJ45/SFP/SFP+)
					 bnameET1D2S08SX1E(700441),            --S12700,8-Port 10GBASE-X and 8-Port 100/1000BASE-X and 8-Port 10/100/1000BASE-T Combo Interface Card(XF,RJ45/SFP/SFP+)
					 bnameEH1D2PS00P00(700442),            --S12700,Open Service Platform Unit
					 bnameET1D200CMU00(700443),            --S12700,Centralized Monitoring Board
					 bnameET1D2MPUA000(700444),            --S12700,Main Processing Unit A,Optional clock
					 bnameET1D2SFUA000(700445),            --S12700,S12708/S12712,Switch Fabric Unit A
					 bnameET1D2SFUD000(700446),            --S12700,S12708/S12712,Switch Fabric Unit D
					 bnameET1D2ACU2000(700447),            --S12700,ACU2
					 bnameET1D2SFUC000(700448),            --S12700,S12708/S12712,Switch Fabric Unit C
					 bnameET1D2IPS0S00(700449),            --S12700/9700/7700,IPS/IDS Unit
					 bnameET1D2FW00S00(700450),            --S12700/9700/7700,10G Firewall Unit
					 bnameET1D2FW00S01(700451),            --S12700/9700/7700,20G Firewall Unit
					 bnameET1D2FW00S02(700452),            --S12700/9700/7700,40G Firewall Unit


	-- SSP & NSE:
					 bnameSSP302X10GL(571003),              -- SSP30-2x10GE-LAN-XFP
					 bnameSSP302X10GW(571004),              -- SSP30-2x10GE-WAN-XFP
					 bnameSSP301X10GL(571005),              -- SSP30-1x10GE-LAN-XFP
					 bnameSSP301X10GW(571006),              -- SSP30-1x10GE-WAN-XFP
					 bnameSSP3020GSF(571007),               -- SSP30-20xGE-SFP
					 bnameSSP3010GSF(571008),               -- SSP30-10xGE-SFP
					 bnameSSP3024GTX(571009),               -- SSP30-24xGE-TX
					 bnameSSP3048GTX(571010),               -- SSP30-48xGE-TX
					 bnameSSP302XP64X(571011),              -- SSP30-2xPOS/STM64-XFP
					 bnameSSP301XP64X(571012),              -- SSP30-1xPOS/STM64-XFP
					 bnameSSP308XP16S(571013),              -- SSP30-8xPOS/STM16-SFP
					 bnameSSP304XP16S(571014),              -- SSP30-4xPOS/STM16-SFP
					 bnameSSP302XP16S(571015),              -- SSP30-2xPOS/STM16-SFP
					 bnameSSP301XP16S(571016),              -- SSP30-1xPOS/STM16-SFP
					 bnameSSP308XP4S(571017),               -- SSP30-8xPOS/STM4-SFP
					 bnameSSP304XP4S(571018),               -- SSP30-4xPOS/STM4-SFP
					 bnameSSP308XP1S(571019),               -- SSP30-8xPOS/STM1-SFP
					 bnameSSP201X10GLLPUA(571020),          -- SSP20-1x10GE-LAN-XFP LPUA
					 bnameSSP201X10GLLPUG(571021),          -- SSP20-1x10GE-LAN-XFP LPUG
					 bnameSSP201X10GWLPUA(571022),          -- SSP20-1x10GE-WAN-XFP LPUA
					 bnameSSP201X10GWLPUG(571023),          -- SSP20-1x10GE-WAN-XFP LPUG
					 bnameSSP2010GSLPUA(571024),            -- SSP20-10xGE-SFP LPUA
					 bnameSSP2010GSLPUG(571025),            -- SSP20-10xGE-SFP LPUG
					 bnameSSP205GSLPUA(571026),             -- SSP20-5xGE-SFP  LPUA
					 bnameSSP205GSLPUG(571027),             -- SSP20-5xGE-SFP  LPUG
					 bnameSSP2024GTLPUA(571028),            -- SSP20-24xGE-TX  LPUA
					 bnameSSP2024GTLPUG(571029),            -- SSP20-24xGE-TX  LPUG
					 bnameSSP2024GFSLPUG(571030),           -- SSP20-24xGE/FE-SFP  LPUG
					 bnameSSP20PS64LPUA(571031),            -- SSP20-POS/STM64-XFP LPUA
					 bnameSSP20PS64LPUG(571032),            -- SSP20-POS/STM64-XFP LPUG
					 bnameSSP204PS64LPUA(571033),            -- SSP20-4xPOS/STM16-SFP LPUA
					 bnameSSP204PS64LPUG(571034),            -- SSP20-4xPOS/STM16-SFP LPUG
					 bnameSSP202XPS16LPUA(571035),          -- SSP20-2xPOS/STM16-SFP LPUA
					 bnameSSP202XPS16LPUG(571036),          -- SSP20-2xPOS/STM16-SFP LPUG
					 bnameSSP201XPS16LPUA(571037),          -- SSP20-POS/STM16-SFP LPUA
					 bnameSSP201XPS16LPUG(571038),          -- SSP20-POS/STM16-SFP LPUG
					 bnameSSP204XPS4LPUA(571039),           -- SSP20-4xPOS/STM4-SFP LPUA
					 bnameSSP204XPS4LPUG(571040),           -- SSP20-4xPOS/STM4-SFP LPUG
					 bnameSSP208XPS1LPUA(571041),           -- SSP20-8xPOS/STM1-SFP LPUA
					 bnameSSP208XPS1LPUG(571042),           -- SSP20-8xPOS/STM1-SFP LPUG
					 bnameSSP204XPS1LPUA(571043),           -- SSP20-4xPOS/STM1-SFP LPUA
					 bnameSSP204XPS1LPUG(571044),           -- SSP20-4xPOS/STM1-SFP
					 bnameSSPDEVOPM(571045) ,                      -- SSP10-OPM Module
					 bnameNSESX11LPUF10(571046),                     -- SX11LPUF1020
					 bnameNSESX11LPUF20(571047),                     -- SX11LPUF2020
					 virentSSP5000SX1D0MPUB460(696500),     --virentSSP5000SX1D0MPUB460
					 virentSSP5000SX1D0SRUA570(696501),     --virentSSP5000SX1D0SRUA570
					 virentSSP5000SX1DLPUFA070(696502),     --virentSSP5000SX1DLPUFA070
					 virentSSP5000SX1DSFUIE07B(696503),     --virentSSP5000SX1DSFUIE07B
					 virentSSP5000SX1DSFUIE07C(696504),     --virentSSP5000SX1DSFUIE07C
					 virentSSP5000CR57FRA200A(696505),      --virentSSP5000CR57FRA200A
	  -- ATN:
					 bnameATNDEVUNKNOWN(225280),           -- Unknown board type
					 bnameATNDEVMPUG(225281),              -- Main Processing Unit G(Including 1*1G CF Card)
					 bnameATNDEVNPUI20(225282),            -- Network Processing Unit Integrated with 2-Port 10GBase LAN/WAN-XFP
					 bnameATNDEVPIUD(225283),              -- Power Supply Unit
	-- ATN 910&950,950B:
					 bnameATNANC1PIU(225295),        --Power board, 910 and 910I
					 bnameATNANC1FAN(225396),        --Fan board, 910 and 910I
					 bnameATNAND1PIU(225397),        --Power board, 950 and 950B
					 bnameATNAND1FAN(225398),        --Fan board, 950 and 950B
					 bnameATN910IPIU(225340),        --Power board, 910I-AC
					 bnameATNGENERAL(229000),        --The general type

	 --PTN:
					 -- for PTN7900 V100R006C00 2013-8-8 by lishaobin begin
					 bnamePTN7900TPA1SCA(229376),    --TPA1SCA,System Control,Communication and Auxiliary Process Unit,1*1
					 bnamePTN7900TPA1EX12(229377),   --TPA1EX12,12ch 10 Gigabit Ethernet Switching Processing Board-1*1
					 bnamePTN7900TPA1EG24(229378),   --TPA1EG24, 24-Port Gigabit Ethernet Processing Board,1*1
					 bnamePTN7900TPA1EXL2(229379),   --TPA1EXL2,2ch 40 Gigabit Ethernet Switching Processing Board,1*1
					 bnamePTN7900TPA1EH1(229380),    --TPA1EH1,1 Ports 100GE Ethernet Processing Board
					 bnamePTN7900TPA1XCS(229381),    --TPA1XCS,Switch Fabric Unit,1*1
					 bnamePTN7900TPA1EX8(229382),    --TPA1EX8,8ch 10 Gigabit Ethernet Switching Processing Board-1*1
					 bnamePTN7900TPA1CH1(229383),    --TPA1CH1,16 Channels STM-1 CES Optical Interface board ,1*1
					 bnamePTN7900TPA1CQ4(229384),    --TPA1CQ4,4 Channels STM-4 CES Optical Interface board ,1*1
					 bnamePTN7900TPA1FAN(229385),    --TPA1FAN, fan board
					 bnamePTN7900TPA1PIU(229386),    --TPA1PIU,Power board
					 bnamePTN7900TPA1EFI(229387),    --TPA1EFI,EMI Filter Interface Board
					 -- FOR package board
					 bnamePTN7900TPA1EX4(229388),   --TPA1EX4,12ch 10 Gigabit Ethernet Switching Processing Board-1*1
					 bnamePTN7900TPA1EXL1(229389),  --TPA1EXL1,1ch 40 Gigabit Ethernet Switching Processing Board,1*1
					 bnamePTN7900TPA1CO1(229390),   --TPA1CO1,8ch Channels STM-1 CES Optical Interface board ,1*1
					 bnamePTN7900TPA1EG16(229391),  --TPA1EG16, 16-Port Gigabit Ethernet Processing Board,1*1
					 -- FOR PTN7900-24
					 bnamePTN7900TPB1CXP(229392),    --TPB1CXP,System Control Communication and Switch Fabric Process Unit,1*1
					 bnamePTN7900TPB1XCS(229393),    --TPB1XCS,Switch Fabric Unit,1*1
					 bnamePTN7900TPB1FAN(229394),    --TPB1FAN, fan board
					 bnamePTN7900TPB1PIU(229395),    --TPB1PIU,Power board
					 bnamePTN7900TPB1PSU(229396),    --TPB1PSU,PSU Power board
					 -- for PTN7900 V100R006C00 2013-8-8 by lishaobin end
					 -- for PTN POTN&100G 80KM begin
					 bnamePTN7900TPA1EH1A(229397),   --TPA1EH1A,1-port WAN 80km 100 Gigabit Ethernet Switching Processing Board
					 bnamePTN7900TPA1UH1(229398),    --TPA1UH1,1-port 100 Gigabit Ethernet and OTN Hybrid Line Card
					 bnamePTN7900TPA1UX10(229399),   --TPA1UX10,10-port 10 Gigabit Ethernet and OTN Hybrid Line Card
					 bnamePTN790TPA1UH1A(229400),    --TPA1UH1A,1-port 100 Gigabit Ethernet and OTN PIC Hybrid Line Card
					 bnamePTN7900TPA1TG30(229401),   --TPA1TG30,30-port 1 Gigabit Ethernet OTN Tributary Card
					 bnamePTN7900TPA1TX10(229402),   --TPA1TX10,10-port 10 Gigabit Ethernet OTN Tributary Card
					 -- for PTN POTN&100G 80KM end by zhangyi 2014-3-14

-- AR:          0x000A3000~0x000A3fff(667648~671743)
					 bnameAR1220(667648),                   -- AR1220 Main Control Unit
					 bnameAR1220W(667649),                  -- AR1220W Main Control Unit
					 bnameAR1240(667650),                   -- AR1240 Main Control Unit
					 bnameAR1240W(667651),                  -- AR1240W Main Control Unit
					 bnameAR2220(667652),                   -- AR2220 Main Control Unit
					 bnameAR2240(667653),                   -- AR2240 Main Control Unit
					 bnameAR3260(667654),                   -- AR3260 Main Control Unit
					 bnameAR01WMF9TTA(667655),              -- 8 Port 100BASE-RJ45 and 1 Port 1000BASE- RJ45  L2/L3 Ethernet Interface Card
					 bnameAR01XEGFTA(667656),               -- 24 Port 1000BASE-RJ45-L2/L3  Ethernet Interface Card
					 bnameAR01XEGFVA(667657),               -- 24 Port  1000BASE-RJ45-L2/L3 with POE Ethernet Interface Card
					 bnameAR01SEG1CA(667658),               -- 1 Port GE Combo WAN Interface Card
					 bnameAR01SEF2TA(667659),               -- 2 Port FE WAN Interface Card
					 bnameAR01SDE11A(667660),               -- 1 Port Unchannelized E1/Unstructure E1/Fractional E1, WAN Interface Card
					 bnameAR01SDME1A(667661),               -- 1 Port Channelized E1/PRI/VE1 ;MFT:Multiflex Trunk
					 bnameAR01SDT11A(667662),               -- 1 Port Unchannelized T1/Unstructure T1/Fractional T1,  WAN Interface Card
					 bnameAR01SDMT1A(667663),               -- 1 Port Channelized T1/PRI/VT1 ;MFT:Multiflex Trunk
					 bnameAR01SDE12A(667664),               -- 2 Port Unchannelized E1/Unstructure E1/Fractional E1,1WAN Interface Card
					 bnameAR01SDME2A(667665),               -- 2 Port Channelized E1/PRI/VE1 ;MFT:Multiflex Trunk
					 bnameAR01SDT12A(667666),               -- 2 Port Unchannelized T1/Unstructure T1/Fractional T1,  WAN Interface Card
					 bnameAR01SDMT2A(667667),               -- 2 Port Channelized T1/PRI/VT1 ;MFT:Multiflex Trunk
					 bnameAR01SDSA1A(667668),               -- 1 Port Sync Serial WAN Interface Card
					 bnameAR01WDAS8A(667669),               -- 8 Port Async Serial  WAN Interface Card
					 bnameAR01SDS1XA(667670),               -- 1 Port ISDN S/T WAN Interface Card
					 bnameAR01SVS2XA(667671),               -- 2 Port ISDN S/T Voice Interface Card
					 bnameAR01SVA4B1A(667672),              -- 4 Port FXS and 1-Port FXO voice  Interface Card
					 bnameAR01SVB4XA(667673),               -- 4 Port FXO voice  Interface Card
					 bnameAR01WVAHXA(667674),               -- 32 Port FXS voice  Interface Card
					 bnameAR01SLA1XA(667675),               -- 1-Port ADSL2+ annex A/M WAN Interface Card
					 bnameAR01SLB1XA(667676),               -- 1-Port ADSL2+ annex B WAN Interface Card
					 bnameAR01SLS1XA(667677),               -- 1-Port-4 pair G.SHDSL WAN Interface Card
					 bnameAR01SOPP2A(667678),               -- 1-Port GPON/EPON dual-mode interface Card
					 bnameAR01FAN(667679),                  -- Fan Card
					 bnameAR01PWR(667680),                  -- Power Card, 150W AC
					 bnameAR1220V(667681),                  -- AR1220V Main Control Unit
					 bnameAR201(667682),                    -- AR201 Main Control Unit
					 bnameAR206(667683),                    -- AR206 Main Control Unit
					 bnameAR207(667684),                    -- AR207 Main Control Unit
					 bnameAR207V(667685),                   -- AR207V Main Control Unit
					 bnameAR208E(667686),                   -- AR208 Main Control Unit
					 bnameAR01SDSA2A(667687),               -- 2 Port Sync Serial WAN Interface Card
					 bnameAR01CPOS(667688),                 -- 155M CPOS Card
					 bnameAR01VDSL2(667689),                -- 2 Port VDSL2 Card
					 bnameAR1220VW(667690),                 -- AR1220VW Main Control Unit
					 bnameAR207VP(667693),                  -- AR207V-P Main Control Unit
					 bnameAR201S(667694),                   -- AR201-S Main Control Unit
					 bnameAR207S(667695),                   -- AR207-S Main Control Unit
					 bnameAR151(667696),                    -- AR151 Main Control Unit
					 bnameAR157(667697),                    -- AR157 Main Control Unit
					 bnameAR01WDME2A(667698),               -- 2-Port Channelized E1/T1/PRI/VE1 Multiflex Trunk Interface Card (WSIC),1*2
					 bnameAR01WVS2XA(667699),               -- 2-Port ISDN S/T Voice Interface Card (WSIC),1*2
					 bnameAR2220S(667700),                 -- AR2220-S Main Control Unit
					 bnameAR1220L(667701),                 -- AR1220L Main Control Unit
					 bnameAR207GHSPA7(667702),             -- AR207G-HSPA+7 Main Control Unit
					 bnameAR01WEG4SA(667703),              -- 4-Port GE SFP WAN Interface Card
					 bnameAR01WEG4TA(667704),              -- 4-Port GE Copper WAN Interface Card
					 bnameAR01SLV1XA(667705),              -- 1-Port VDSL2 WAN Interface Card
					 bnameAR01SDGW1A(667706),              -- WCDMA Data Card
					 bnameAR01WSX220A(667708),             -- SAE220 WSIC Card
					 bnameAR01XSX550A(667709),             -- SAE550 XSIC Card
					 bnameSRG1320V(667710),                -- SRG1320V Main Control Unit
					 bnameSRG1320VW(667711),               -- SRG1320VW Main Control Unit
					 bnameSRG2320(667712),                 -- SRG2320 Main Control Unit
					 bnameSRG3340(667713),                 -- SRG3340 Main Control Unit
					 bnameSRG3360(667714),                 -- SRG3360 Main Control Unit
					 bname16FXS(667715),                   -- 16FXS Card
					 bnameAR156(667716),                   -- AR156 Main Control Unit
					 bnameAR158E(667717),                  -- AR158E Main Control Unit
					 bnameAR151GHSPA(667718),              -- AR151G-HSPA+7 Main Control Unit
					 bnameAR157GHSPA(667719),              -- AR157G-HSPA+7 Main Control Unit
					 bnameAR151WP(667720),                 -- AR151W-P Main Control Unit
					 bnameAR157W(667721),                  -- AR157W Main Control Unit
					 bnameAR158EGVWHSPA(667722),           -- AR158EGVW-HSPA+7-P Main Control Unit
					 bnameAR157VW(667723),                 -- AR157VW Main Control Unit
					 bnameAR158EVW(667724),                -- AR158EVW Main Control Unit
					 bnameAR2201(667725),                  -- AR2201 Main Control Unit
					 bnameAR2202(667726),                  -- AR2202 Main Control Unit
					 bnameAR2220L(667727),                 -- AR2220L Main Control Unit
					 bnameAR201VWP(667728),                -- AR201VWP Main Control Unit
					 bnameAR207VW(667729),                 -- AR207VW Main Control Unit
					 bnameAR2230(667730),                  -- AR2230 Main Control Unit
					 bnameAR2220D(667731),                 -- AR2220D Main Control Unit
					 bnameAR2204(667732),                  -- AR2204 Main Control Unit
					 bnameSRU60(667733),                   -- SRU60 Main Control Unit
					 bnameUSR206(667734),                  -- USR20-6 Main Control Unit
					 bnameUSR208(667735),                  -- USR20-8 Main Control Unit
					 bnameHSE5(667736),                    -- HSE5 Main Control Unit
					 bnameAR8CE1T1(667737),                -- 8E1/T1-M Control Unit
					 bnameAR4CE1T1(667738),                -- 4E1/T1-M Control Unit
					 bnameAR1POS(667739),                  -- 1POS-155M Control Unit
					 bnameARIMA(667740),                   -- 4E1-IMA Control Unit
					 bnameAR4FE1(667741),                  -- 4E1/T1-F Control Unit
					 bnameAR8FE1(667742),                  -- 8E1/T1-F Control Unit
					 bnameAR4GEL2 (667743),                -- 4GE-L2 Control Unit
					 bnameSRG303W(667744),                 -- SRG303W Main Control Unit
					 bnameSRG303VW(667745),                -- SRG303VW Main Control Unit
					 bnameSRG2320D(667746),                -- SRG2320D Main Control Unit
					 bnameSRG2304(667747),                 -- SRG2304 Main Control Unit
					 bnameSRG2330(667748),                 -- SRG2330 Main Control Unit
					 bnameSRG1320(667749),                 -- SRG1320 Main Control Unit
					 bnameSRG1320W(667750),                -- SRG1320W Main Control Unit
					 bnameAR1CE3(667751),                  -- 1CE3 Control Unit
					 bnameAR1STM4(667752),                 -- 1POS-622M Control Unit
					 bnameAR3CE3(667753),                  -- 3CE3 Control Unit
					 bnameAR1CPOS155MW(667754),            -- 1CPOS-155M-W Control Unit
					 bnameAR1220S(667755),                 -- AR1220-S Main Control Unit
					 bnameAR1220WS(667756),                -- AR1220W-S Main Control Unit
					 bnameAR1220D(667757),                 -- AR1220-D Main Control Unit
					 bnameAR3GEVDOA(667758),               -- 3G-EVDOA Control Unit
					 bnameAR151GEVDO(667759),              -- AR151G-EVDO Main Control Unit
					 bnameAR156I(667760),                  -- AR156I Main Control Unit
					 bnameAR156IW(667761),                 -- AR156IW Main Control Unit
					 bnameAR157I(667762),                  -- AR157I Main Control Unit
					 bnameAR157IW(667763),                 -- AR157IW Main Control Unit
					 bnameAR168F(667764),                  -- AR168F Main Control Unit
					 bnameAR168FW(667765),                 -- AR168FW Main Control Unit
					 bnameAR169F(667766),                  -- AR169F Main Control Unit
					 bnameAR169W(667767),                  -- AR169W Main Control Unit
					 bnameAR169FW(667768),                 -- AR169FW Main Control Unit
					 bnameAR169BF(667769),                 -- AR169BF Main Control Unit
					 bnameAR169BFW(667770),                -- AR169BFW Main Control Unit
					 bnameAR1220F(667771),                 -- AR1220F Main Control Unit
					 bnameAR1220FW(667772),                -- AR1220FW Main Control Unit
					 bnameAR151S(667773),                  -- AR151-S Main Control Unit
					 bnameAR151WPS(667774),                -- AR151W-P-S Main Control Unit
					 bnameAR151GUS(667775),                -- AR151G-U-S Main Control Unit
					 bnameAR1220LS(667776),                -- AR1220L-S Main Control Unit
					 bnameAR220148FES(667777),             -- AR2201-48FE-S Main Control Unit
					 bnameAR2204S(667778),                 -- AR2204-S Main Control Unit
					 bnameAR159(667779),                   -- AR159 Main Control Unit
					 bname3G1EVDO(667780),                 -- 3G-EVDOA Control Unit
					 bname24GEV(667781),                   -- 24GEV Control Unit
					 bname4ES2GS(667782),                  -- 4ES2G-S Control Unit
					 bname4ES2GPS(667783),                 -- 4ES2GP-S Control Unit
					 bname9ES2(667784),                    -- 9ES2 Control Unit
					 bname1CE3T3M(667785),                 -- 1CE3T3M Control Unit
					 bnameLTEH(667786),                    -- LTE-H Control Unit
					 bname1VE1T1(667787),                  -- 1VE1/T1 Control Unit
					 bname1ADSLBJ(667788),                 -- 1ADSL-BJ Control Unit
					 bname1NDE(667789),                    -- 1NDE Control Unit
					 bnameAR531GPH(667790),                -- AR531GP-H Main Control Unit
					 bnameAR531GBPDH(667791),              -- AR531GBP-D-H Main Control Unit
					 bnameAR5312CH(667792),                -- AR531-2C-H Main Control Unit
					 bnameAR531F2CH(667793),               -- AR531-F2C-H Main Control Unit
					 bnameAR2540H(667794),                 -- AR2540-H Main Control Unit
					 bnameAR3560H(667795),                 -- AR3560-H Main Control Unit
					 bnameSRU400(667796),                  -- SRU400 Main Control Unit
					 bnameSRU200(667797),                  -- SRU200 Main Control Unit
					 bnameSRU100(667798),                  -- SRU100 Main Control Unit
					 bnameAR4STM1(667799),                 -- 4STM-1 Control Unit
					 bnameARALARM(667800),                 -- Alarm Control Unit
					 bnameAR8SA(667801),                   -- 8SA/AS Control Unit
					 bnameAR6EM(667802),                   -- 6E&M Control Unit
					 bnameAR4GECOMBO(667803),              -- 4GE COMBO Control Unit
					 bnameAR2240S(667804),                 -- AR2240-S Main Control Unit
					 bnameMSP40(667805),                   -- NE16EX-8 Main Control Unit
					 bnameAR9ES3P(667806),                 -- 9ES3P Control Unit
					 bnameAR01PWR150D(667807),             -- Power Card, 150W DC
					 bnameAR01PWR350A(667808),             -- Power Card, 350W AC
					 bnameAR01PWR350D(667809),             -- Power Card, 350W DC
					 bnameAR121S(667810),                  -- AR121-S Main Control Unit
					 bnameAR161FS(667811),                 -- AR161F-S Main Control Unit
					 bnameAR156W(667812),                  -- AR156W Main Control Unit
					 bnameAR8FE1GE8POE(667813),            -- WSIC-8FE1GE (8POE) Control Unit
					 bnameAR4FXS1FXO(667814),              -- SIC-4FXS1FXO Control Unit
					 bnameAR159FW(667815),                 -- AR159FW Main Control Unit
					 bnameAR161FGWL(667816),               -- AR161FGW-L Main Control Unit
					 bnameAR161FGL(667817),                -- AR161FG-L Main Control Unit
					 bnameMSP20(667818),                   -- NE16EX-6 Main Control Unit
					 bnameSRG2320E(667819),         	      -- SRG2320E Main Control Unit
					 bnameAR162F(667820),                  -- AR162F Main Control Unit
					 bnameAR169FVW(667821),                -- AR169FVW Main Control Unit
					 bnameAR161FW-P-M5(667822),            -- AR161FW-P-M5 Main Control Unit
					 bnameAR511GW-UAV2M5(667823),          -- AR511GW-UAV2M5 Main Control Unit
					 bnameAR169GFVW-L(667824),             -- AR169GFVW-L Main Control Unit
					 bnameAR531GBP-U-H(667825),            -- AR531GBP-U-H Main Control Unit
					 bnameAR161FW(667826),                 -- AR161FW Main Control Unit
					 bnameAR1220F-S(667827),               -- AR1220F-S Main Control Unit
					 bnameARTDDLTE(667829),                -- TDD-LTE SIC Card
					 bnameAR511GW-LAV2M3(667830),          -- AR511GW-LAV2M3 Main Control Unit
					 bnameAR161A(667831),                  -- AR161A Main Control Unit
					 bnameAR169A(667832),                  -- AR169A Main Control Unit
					 bnameAR161AG-L(667833),               -- AR161AG-L Main Control Unit
					 bnameAR169AGW-I(667834),              -- AR169AGW-I Main Control Unit
					 bnameAR1220EVW(667835),               -- AR1220EVW Main Control Unit
					 bnameAR2220E(667836),                 -- AR2220E Main Control Unit
					 bnameAR3670-SRUx5(667837),            -- AR3670 (SRUx5) Main Control Unit
					 bnameAR3650(667838),                  -- AR3650 Main Control Unit
					 bnameAR2630(667839),                  -- AR2630 Main Control Unit
					 bnameAR2204E(667840),                 -- AR2204E Main Control Unit
					 bnameAR2220E-L(667841),               -- AR2220E-L Main Control Unit
					 bnameAR511GW-L-B3(667842),            -- AR511GW-L-B3 Main Control Unit
					 bnameAR511GW-LM7(667843),             -- AR511GW-LM7 Main Control Unit
					 bnameAR513W-V3M8(667844),             -- AR513W-V3M8 Main Control Unit
					 bnameAR1220E-S(667845),               -- AR1220E-S Main Control Unit
					 bnameAR3260-S(667846),                -- AR3260-S Main Control Unit
					 bnameAR531G-U-D-H(667847),            -- AR531G-U-D-H Main Control Unit
					 bnameAR531GPe-U-H(667848),            -- AR531GPe-U-H Main Control Unit
					 bnameAR531GR-U-H(667849),             -- AR531GR-U-H Main Control Unit
					 bnameAR550-8FE-D-H(667850),           -- AR550-8FE-D-H Main Control Unit
					 bnameAR550-24FE-D-H(667851),          -- AR550-24FE-D-H Main Control Unit
					 bnameAR502G(667852),                  -- AR502G Main Control Unit
					 bnameAR531GP-H(667853),               -- AR531GP-H Main Control Unit
					 bnameAR531GB-U-D-H(667854),           -- AR531GB-U-D-H Main Control Unit
					 bnameAR161(667855),                   -- AR161 Main Control Unit
					 bnameAR161G-LE(667856),               -- AR161G-LE Main Control Unit
					 bnameAR161G-HSPA7(667857),            -- AR161G-HSPA+7 Main Control Unit
					 bnameAR161GW-L(667858),               -- AR161GW-L Main Control Unit
					 bnameAR169(667859),                   -- AR169 Main Control Unit
					 bnameAR169G-LE(667860),               -- AR169G-LE Main Control Unit
					 bnameAR169G-HSPA7(667861),            -- AR169G-HSPA+7 Main Control Unit
					 bnameAR121(667862),                   -- AR121 Main Control Unit
					 bnameAR129(667863),                   -- AR129 Main Control Unit
					 bnameAR503GW-LM6(667864),             -- AR503GW-LM6 Main Control Unit
					 bnameAR169-P-M9(667865),              -- AR169-P-M9 Main Control Unit
					 bnameAR1220E(667866),                 -- AR1220E Main Control Unit
					 bnameAR1220EV(667867),                -- AR1220EV Main Control Unit
					 bnameARWSIC-1NDE(667868),             -- WSIC-1NDE Control Unit
					 bnameARSIC-LTEC(667869),              -- SIC-LTEC Control Unit
					 bnameARWSIC-GSHDSL(667870),           -- WSIC-G.SHDSL Control Unit
					 bnameAR4GE-POE(667871),               -- 4GE POE Control Unit
					 bnameAR24GE-L2-POE(667872),           -- 24GE-L2-POE Control Unit
					 bnameAR161-S(667873),                 -- AR161-S Main Control Unit
					 bnameAR01PWR850W-PoE(667874),         -- Power Card, 850W POE
					 bnameAR161F(667875),                  -- AR161F Main Control Unit
					 bnameAR169FGW-L(667876),              -- AR169FGW-L Main Control Unit
					 bnameAR1STM-4POS(667877),             -- 4STM-1/1STM-4 POS Control Unit

-- vRGW:        0x000A6000~0x000A6fff(679936~684031)
					 bnameVRGWDEVUNKNOWN(679936),           -- Unknown board type
					 bnameVRGWMPU(679937),                  -- vRGW MPU board
					 bnameVRGWLPU(679938),                  -- vRGW LPU board
					 bnameVRGWGENERAL(684031),               -- The general type

-- CloudEngine: 0x000A8000~0x000A8fff(688128~692223)
					 bnameDE01MPUA(688128),                   -- CloudEngine 12800-CE-MPUA-Main Processing Unit -1*1
					 bnameDE01SFU04C(688129),                 -- CloudEngine CE12804 CE-SFU04C,12804 Switch Fabric Unit-1*1
					 bnameDE01SFU08C(688130),                 -- CloudEngine CE12808 CE-SFU08C,S12808 Switch Fabric Unit-1*1
					 bnameDE01SFU12C(688131),                 -- CloudEngine CE12812 CE-SFU12C,12812 Switch Fabric Unit-1*1
					 bnameDE01X48SAAEA(688132),               -- CloudEngine CE12800 CE-L48XS-EA,48-Port 10GBASE-X Interface Card(SFP+)-1*1
					 bnameDE01X24SAA(688133),                 -- CloudEngine CE12800 CE-L24XS-EA,24-Port 10GBASE-X Interface Card(SFP+)-1*1
					 bnameDE01L24QAA(688134),                 -- CloudEngine CE12800 CE-L24LQ-EA,24-Port-40G Interface Card(QSFP+)-1*1
					 bnameDE01BAK04A(688135),                 -- CloudEngine CE12800 CE-BAK04A,12804 Backplane-1*1
					 bnameDE01BAK08A(688136),                 -- CloudEngine CE12800 CE-BAK08A,12808 Backplane-1*1
					 bnameDE01BAK12A(688137),                 -- CloudEngine CE12800 CE-BAK12A,12812 Backplane-1*1
					 bnameDE51SRU1B(688138),                  -- CloudEngine CE5850 CE5850-48T4S2Q-EI 48-Port GE  RJ45 and 4-Port SFP+ Optical and 2-Port 40GE QSFP+ Optical Switch Control Unit
					 bnameDE51SRU1A(688139),                  -- CloudEngine CE6850 CE6850-48S4Q-EI 48-Port SFP+ Optical and 4-Port 40GE QSFP+ Optical Switch Control Unit
					 bnameDE51SRU1C(688140),                  -- CloudEngine CE6850 CE6850-48T4Q-EI 48-Port 10GBASE-T RJ45 and 4-Port 40GE QSFP+ Optical Switch Control Unit
					 bnameDE01CMUA(688141),                   -- CloudEngine CE12800 CE-CMUA,Centralized MoniToRing Board-1*1
					 bnamePWRAC(688142),                      -- CloudEngine CE5800 CE6800 AC Power Module
					 bnameDE51DFCMA(688143),                  -- CloudEngine CE5800 CE6800 FAN Control Card
					 bnameDE01X48SAASA(688144),               -- CloudEngine CE12800 CE-L48XS-SA,48-Port 10GBASE-X Interface Constringency Card(SFP+)-1*1
					 bnameDE01X48SAAGSEA(688145),             -- CloudEngine CE12800 CE-L48GS-EA,48-Port 1000BASE-X  Interface Card(SFP)-1*1
					 bnameDE01FCMA(688146),                   -- CloudEngine CE12800 FAN-P02,Fan MoniToR and Control Board-1*1
					 bnameDE01POWACA(688147),                 -- CloudEngine CE12800 PAC-2700W-P01,Power Board-1*1
					 bnameDE01SFU04B(688148),                 -- CloudEngine12804,CE-SFU04B,CE12804 Switch Fabric Unit B,1*1
					 bnameDE01SFU08B(688149),                 -- CE12808,CE-SFU08B,CE12808 Switch Fabric Unit B,1*1
					 bnameDE01SFU12B(688150),                 -- CE12812,CE-SFU12B,CE12812 Switch Fabric Unit B,1*1
					 bnameDE01SFU04A(688151),                 -- CloudEngine12804,CE-SFU04A,CE12804 Switch Fabric Unit A,1*1
					 bnameDE01SFU08A(688152),                 -- CE12808,CE-SFU08A,CE12808 Switch Fabric Unit A,1*1
					 bnameDE01SFU12A(688153),                 -- CE12812,CE-SFU12A,CE12812 Switch Fabric Unit A,1*1
					 bnameCEL48GTEA(688154),                  -- CloudEngine 12800,CE-L48GT-EA,48-Port 10/100/1000BASE-T Interface Card(EA,RJ45),1*1
					 bnameCEL48GSEA(688155),                  -- CloudEngine 12800,CE-L48GS-EA,48-Port 100/1000BASE-X Interface Card(EA,SFP),1*1
					 bnameCEL48GTED(688156),                  -- CloudEngine 12800,CE-L48GT-ED,48-Port 10/100/1000BASE-T Interface Card(ED,RJ45)-1*1
					 bnameCEL48GSED(688157),                  -- CloudEngine 12800,CE-L48GS-ED,48-Port 100/1000BASE-X Interface Card(ED,SFP),1*1
					 bnameCEL48XSED(688158),                  -- CloudEngine 12800,CE-L48XS-ED,48-Port-10GE Interface Card(ED,SFP+),1*1
					 bnameCEL48XSEF(688159),                  -- CloudEngine 12800,CE-L48XS-EF,48-Port-10GE Interface Card(EF,SFP+),1*1
					 bnameCEL24XSED(688160),                  -- CloudEngine 12800,CE-L24XS-ED,24-Port-10GE Interface Card(ED,SFP+),1*1
					 bnameCEL24XSEF(688161),                  -- CloudEngine 12800,CE-L24XS-EF,24-Port-10GE Interface Card(EF,SFP+),1*1
					 bnameCEL12LQEA(688162),                  -- CloudEngine 12800,CE-L12LQ-EA,12-Port-40G Interface Card(EA,QSFP+),1*1
					 bnameCEL12LQEF(688163),                  -- CloudEngine 12800,CE-L12LQ-EF,12-Port-40G Interface Card(EF,QSFP+),1*1
					 bnameCEM24T4SP01(688164),                -- CloudEngine CE5810 CE5810-24T4S-EI Switch(24-Port GE RJ45,4-Port 10GE SFP+,Without Fan and Power Module)
					 bnameCEM48T4SP01(688165),                -- CloudEngine CE5810 CE5810-48T4S-EI Switch(48-Port GE RJ45,4-Port 10GE SFP+,Without Fan and Power Module)
					 bnameCEM48T4S2QP02(688166),              -- CloudEngine 5800,CEM48T4S2QP02,48-Port GE RJ45,4-Port SFP+ Optical,2-Port 40GE QSFP+ Optical Switch Control Unit,1*1
					 bnameCEL06LQEA(688167),                  -- CloudEngine 12800,CE-L06LQ-EA,6-Port-40G Interface Card(EA,QSFP+),1*1
					 bnameCEL06LQEF(688168),                  -- CloudEngine 12800,CE-L06LQ-EF,6-Port-40G Interface Card(EF,QSFP+),1*1
					 bnameCESFU16A(688169),                   -- CloudEngine 12800,CE-SFU16A CE12816 Switch Fabric Unit A 1*1
					 bnameCEL12XSED(688171),                  -- CloudEngine 12800,CE-L12XS-ED,12-Port-10GE Interface Card(ED,SFP+),1*1
					 bnameCECMUB(688172),                     -- CloudEngine 12800,CE-CMUB,Centralized Monitoring Board B,1*1
					 bnameCEL48GTEC(688173),                  -- CloudEngine 12800,CE-L48GT-EC,48-Port 10/100/1000BASE-T Interface Card(EC,RJ45),1*1
					 bnameCEL48GSEC(688174),                  -- CloudEngine 12800,CE-L48GS-EC,48-Port 100/1000BASE-X Interface Card(EC,SFP),1*1
					 bnameCEL24XSBA(688175),                  -- CloudEngine 12800,CE-L24XS-BA,24-Port 10GBASE-X Interface Card(BA,SFP+),1*1
					 bnameCEL48XSBA(688176),                  -- CloudEngine 12800,CE-L48XS-BA,48-Port 10GBASE-X Interface Card(BA,SFP+),1*1
					 bnameCESFU16B(688177),                   -- CloudEngine 12800,CE-SFU16B,CE12816 Switch Fabric Unit B,1*1
					 bnameCESFU16C(688178),                   -- CloudEngine 12800,CE-SFU16C,CE12816 Switch Fabric Unit C,1*1
					 bnameCEL04CFEF(688179),                  -- CloudEngine 12800,CE-L04CF-EF,4-Port-100GE Interface Card(EF,CFP),1*1
					 bnameCEL24XSEC(688180),                  -- CloudEngine 12800,CE-L24XS-EC,24-Port-10GE Interface Card(EC,SFP+),1*1
					 bnameCEL48XSEC(688181),                  -- CloudEngine 12800,CE-L48XS-EC,48-Port-10GE Interface Card(EC,SFP+),1*1
					 bnameCEL24LQEC(688182),                  -- CloudEngine 12800,CE-L24LQ-EC,24-Port 40G Interface Card(EC,QSFP+),1*1
					 bnameCEL04CFEA(688183),                  -- CloudEngine 12800,CE-L04CF-EA,4-Port-100GE Interface Card(EA,CFP),1*1
					 bnameCE785032QEI(688184),                -- CloudEngine 7800,CEM32QP01,32-Port 40GE QSFP+ Optical Switch Control Unit,1*1
					 bnameCE681048S4QEI(688185),              -- CloudEngine 6800,CEM48S4QP02,48-Port SFP+ Optical,4-Port 40GE QSFP+ Optical Switch Control Unit,1*1
					 bnameCE681048S4QLI(688186),              -- CloudEngine 6800,CEM48S4QP04,48-Port SFP+ Optical,4-Port 40GE QSFP+ Optical Switch Control Unit,1*1
					 bnameCEL48GTEF(688187),                  -- Manufactured Board,iCE,CE-L48GT-EF,48-Port 10/100/1000BASE-T Interface Card(EF,RJ45)-1*1
					 bnameCE681048SLI(688188),                -- CloudEngine 6800,CEM48SP01,48-Port SFP+ Optical Switch Control Unit,1*1
					 bnameCE685048S6QHI(688189),              -- CloudEngine 6800,CE6850-48S6Q-HI Switch(48-Port 10GE SFP+,6-Port 40GE QSFP+)
					 bnameCEMPUAS(688190),                    -- Manufactured Board,CloudEngine 12800S,CE-MPUA-S
					 bnameCEL48XTEC(688191),                  -- Manufactured Board,CloudEngine 12800,CE-L48XT-EC,1*1
					 bnameCEL12CFEG(688192),                  -- Manufactured Board,CloudEngine 12800,CE-L12CF-EG,12-Port-100GE Interface Card(EG,CFP2),1*1
					 bnameCEFWA(688193),                      -- Manufactured Board,CloudEngine 12800,CE-FWA,Fire Wall Card A,1*1
					 bnameCEL08CCEC(688194),                  -- Manufactured Board,CloudEngine 12800,CE-L08CC-EC,1*1
					 bnameCEL24LQEC1(688195),                 -- Manufactured Board,CE-L24LQ-EC1
					 bnameCESFUBS(688196),                    -- Manufactured Board,CloudEngine 12800S,CE-SFUB-S
					 bnameCESFUCS(688197),                    -- Manufactured Board,CloudEngine 12800S,CE-SFUC-S,CE-SFUC-S,1*1

-- wlan:        0x000A9000~0x000A9fff(692224~696319)
					 bnameH80D2ACMPS00(692224),              --Switching and Routing Unit Board
					 bnameAC6605-26-PWR(692225),             --24port 10/100/1000Base-T 4 1000Base-X
					 bnameAC6005-8(692226),
					 bnameACU2(692227),
					 bnameAP6010SN(692228),
					 bnameAP6010DN(692229),
					 bnameAP6510DN(692231),
					 bnameAP6610DN(692232),
					 bnameAP5010DN(692233),
					 bnameAP5010SN(692234),
					 bnameAP7110DN(692235),
					 bnameAP7110SN(692236),
					 bnameAP3010DN(692237),
					 bnameAP5030DN(692238),
					 bnameAP5130DN(692239),
					 bnameAC6005-8-PWR(692240),
					 bnameAT815SN(692243),
					 bnameAP8030DN(692245),
					 bnameAP8130DN(692246),
					 bnameAP9130DN(692247),
--service board for iODN products: range: 0x000B0000~0x000BFFFF  720,896~786,431
					 bnameAF11TMSA(745473),              -- AF11TMSA
					 bnameAF11TMUA(745474),              -- AF11TMUA
					 bnameAF11TMLA(745475),              -- AF11TMLA
					 bnameAF11TMPA(745476),              -- AF11TMPA
					 bnameAF11STSA(745477),              -- AF11STSA
					 bnameAF11STUA(745478),              -- AF11STUA
					 bnameAF11STLA(745479),              -- AF11STLA
					 bnameAF11STPA(745480),              -- AF11STPA
					 bnameAF11SPSIA(745481),             -- AF11SPSIA
					 bnameAF11SPUIA(745482),             -- AF11SPUIA
					 bnameAF11SPLIA(745483),             -- AF11SPLIA
					 bnameAF11SPPIA(745484),             -- AF11SPPIA
					 bnameAF11SPSHA(745485),             -- AF11SPSHA
					 bnameAF11SPUHA(745486),             -- AF11SPUHA
					 bnameAF11SPLHA(745487),             -- AF11SPLHA
					 bnameAF11SPPHA(745488),             -- AF11SPPHA
					 bnameAF11SPSOA(745489),             -- AF11SPSOA
					 bnameAF11SPUOA(745490),             -- AF11SPUOA
					 bnameAF11SPLOA(745491),             -- AF11SPLOA
					 bnameAF11SPPOA(745492),             -- AF11SPPOA
					 bnameAF11SPSPA(745493),             -- AF11SPSPA
					 bnameAF11SPUPA(745494),             -- AF11SPUPA
					 bnameAF11SPLPA(745495),             -- AF11SPLPA
					 bnameAF11SPPPA(745496),             -- AF11SPPPA
					 bnameAF11SPSJA(745497),             -- AF11SPSJA
					 bnameAF11SPUJA(745498),             -- AF11SPUJA
					 bnameAF11SPLJA(745499),             -- AF11SPLJA
					 bnameAF11SPPJA(745500),             -- AF11SPPJA
					 bnameAF11SPSQA(745501),             -- AF11SPSQA
					 bnameAF11SPUQA(745502),             -- AF11SPUQA
					 bnameAF11SPLQA(745503),             -- AF11SPLQA
					 bnameAF11SPPQA(745504),             -- AF11SPPQA
					 bnameAF11SPSKA(745729),             -- AF11SPSKA
					 bnameAF11SPUKA(745730),             -- AF11SPUKA
					 bnameAF11SPLKA(745731),             -- AF11SPLKA
					 bnameAF11SPPKA(745732),             -- AF11SPPKA
					 bnameAF11SPSRA(745733),             -- AF11SPSRA
					 bnameAF11SPURA(745734),             -- AF11SPURA
					 bnameAF11SPLRA(745735),             -- AF11SPLRA
					 bnameAF11SPPRA(745736),             -- AF11SPPRA
					 bnameAF11SPSLA(745737),             -- AF11SPSLA
					 bnameAF11SPULA(745738),             -- AF11SPULA
					 bnameAF11SPLLA(745739),             -- AF11SPLLA
					 bnameAF11SPPLA(745740),             -- AF11SPPLA
					 bnameAF11SPSSA(745741),             -- AF11SPSSA
					 bnameAF11SPUSA(745742),             -- AF11SPUSA
					 bnameAF11SPLSA(745743),             -- AF11SPLSA
					 bnameAF11SPPSA(745744),             -- AF11SPPSA
					 bnameAF11SPSMA(745745),             -- AF11SPSMA
					 bnameAF11SPUMA(745746),             -- AF11SPUMA
					 bnameAF11SPLMA(745747),             -- AF11SPLMA
					 bnameAF11SPPMA(745748),             -- AF11SPPMA
					 bnameAF11SPSTA(745749),             -- AF11SPSTA
					 bnameAF11SPUTA(745750),             -- AF11SPUTA
					 bnameAF11SPLTA(745751),             -- AF11SPLTA
					 bnameAF11SPPTA(745752),             -- AF11SPPTA
					 bnameAF11STUB(745985),              -- AF11STUB
					 bnameAF11STSB(745986),              -- AF11STSB
					 bnameAF11STLB(745987),              -- AF11STLB
					 bnameAF11STPB(745988),              -- AF11STPB
					 bnameAF11STUC(745989),              -- AF11STUC
					 bnameAF11STSC(745990),              -- AF11STSC
					 bnameAF11STLC(745991),              -- AF11STLC
					 bnameAF11STPC(745992),              -- AF11STPC
					 bnameAF11TMUB(745993),              -- AF11TMUB
					 bnameAF11TMSB(745994),              -- AF11TMSB
					 bnameAF11TMLB(745995),              -- AF11TMLB
					 bnameAF11TMPB(745996),              -- AF11TMPB
					 bnameAF11TMUC(745997),              -- AF11TMUC
					 bnameAF11TMSC(745998),              -- AF11TMSC
					 bnameAF11TMLC(745999),              -- AF11TMLC
					 bnameAF11TMPC(746000),              -- AF11TMPC
--hwRPS
					 bnameCMU01(786632),              --Monitoring module board,with 0 port.
					 bnameCFS01(786633),              --Fan module board,with 3 fan ports
					 bnameCPF318Power(786634),        --Power input module board,with 0 port
					 bnameCCM08(786635),              --Up converter module board,with 8 DC output ports
					 bnameRC12S(786636),              --Down converter module board,with 12 DC input ports
					 bnameCPF104Power(786637),        --BT-C Power input module board,with 0 port
					 bnameCCM08B(786638),             --BT-C Up converter module board,with 8 DC output ports
					 bnameRCM08(786639),              --BT-C Down converter module board,with 12 DC input ports
					 bnameCFS02Power(786640),         --BT-C Power input module board,with 0 port
					 bnameCFS02Monitor(786641),       --BT-C Fan module board,with 3 fan ports
					 bnameETP4830A1-Power(786642),    --BT-C AC-DC System monitor input module board,with 0 port
					 bnameETP4890A2-Power(786642),    --BT-C AC-DC System monitor input module board,with 0 port
					 bnameETP48150A3-Power(786644),   --BT-C AC-DC System monitor input module board,with 0 port
					 bnameSMU01B(786645),             --AC-DC System monitor Monitoring module board
					 bnameSMU01C(786657),             --AC-DC System monitor Monitoring module board
					 bnameR4830G1(786646),            --AC-DC System Power Supply Unit
					 bnameR4830N2(786647),            --AC-DC System Power Supply Unit
					 bnameR4815G1(786648),            --AC-DC System Power Supply Unit
					 bnameR4815N1(786649),            --AC-DC System Power Supply Unit
					 bnameCFS01Power(786650),         --RTF-C Power input module board,with 0 port
					 bnameCVM02(786651),              --RTF-V Up converter module board,with 8 DC output ports
					 bnameCFS01Power2(786652),         --RTF-V Power input module board,with 0 port
					 bnameRPF106Power(786653),        --RTF-V Power input module board,with 0 port
					 bnameRMU01(786654),              --RTF-V Monitoring module board,with 0 port
					 bnameRFS01(786655),              --RTF-V Fan module board,with 3 fan ports
					 bnameRVM04(786656),              --RTF-V Down converter module board,with 12 DC input ports


--Security Product's TC-MIB value scope :       16711680 ~ 16777215  or Hex format:0x00ff0000 ~ 0x00ffffff  (Both 16711680 and 16777215 are included)

--USG2000/USG2100/Eudemon200E
					 bnameFWF1MPUA(16719872),          -- FWF1MPUA,Main Process Unit Board,1*1  USG2100
					 bnameFWF1MPUB(16719873),          -- FWF1MPUB,Main Process Unit Board,1*1  USG2100
					 bnameFWF1ADPA2(16719874),          -- FWF1ADPA,ADSL2+ MIC,3*1)  USG2100/USG2200
					 bnameFWF1F1E12(16719875),          -- FWF1F1E1,1-PORT E1 Interface Board,3*1  USG2100/USG2200
					 bnameFWF1F1CE1(16719876),         -- FWF1F1CE1,1-PORT CE1 Interface Board(DB15),3*1)  USG2100
					 bnameFWF1E1FE2(16719877),          -- FWF1E1FE,1-Port Fast Ethernet Electrical Interface Board(RJ45),3*1  USG2100/USG2200
					 bnameFWF1E5FEA2(16719878),         -- FWF1E5FEA,5-Port Fast Ethernet Switch Electrical Interface Board(RJ45),3*1)  USG2100/USG2200
					 bnameFWG1MPUA2(16719879),          -- FWG1MPUA,Main Process Unit Board,1*1  USG2200
					 bnameFWG1E1GE2(16719880),          -- FWG1E1GE,1-port GE Electrical Interface Card(RJ45),1*1  USG2200
					 bnameFWG1C2E1(16719881),          -- FWG1C2E1,2-port Channelized E1 Interface Card,1*1  USG2200
					 bnameFWG1F1SA2(16719882),      -- USG2200,FWG1F1SA ,1-Channel Sync/Async Serial Port  Interface Card,3*1
					 bnameFWG1WIFI(16719883),      -- USG2200,FWG1WIFI,WiFi MIC Card
					 bnameFWG1F2E12(16719884),      -- USG2200,FWG1F2E1,2-port E1&Fractional E1 Interface Card,1*1
					 bnameFWG1E180(16719885),          -- USG2200,Wireless Data Card,E180,HSUPA/HSDPA/UMTS/EDGE/GPRS/GSM USB STICK,White,HUAWEI Standard
					 bnameFWG1ET128(16719886),         --USG2200,Wireless Data Card,ET128,HSDPA/TD-SCDMA/EDGE/GPRS/GSM USB STICK,HUAWEI Standard Version
					 bnameFWG1EC169(16719887),         --USG2200,Wireless Data Card,EC169,CDMA2000 EV-DO Rev.A Rotatable USB Stick,White,Chinese Universal,RoHS
					 bnameFWF2MPUA(16719888),          --USG2100,FWF2MPUA,USG2100 Main Process Unit,1*1
					 bnameFWF2MPUB(16719889),          --USG2100,FWF2MPUB,USG2100 Main Process Unit,1*1
					 bnameFWF2MPUC(16719890),          --USG2100,FWF2MPUC,USG2100 Main Process Unit,1*1
					 bnameFWF2DB1M(16719891),          --USG2100,FWF2DB1M,USG2100 MIC Daughter Board,2*2
					 bnameSU11FSHL(16719892),          --SRG20,SU11FSHL,4 Channel G.shdsl Interface Board,3*1
					 bnameSU11FSHLB(16719893),         --SRG20,SU11FSHLB,2 Channel G.shdsl Interface Board,3*1
					 bnameSU11FSHLC(16719894),         --SRG20,SU11FSHLC,1 Channel G.shdsl Interface Board,3*1
					 bnameSU11F2SA(16719895),          --USG2200,SU11F2SA ,2-Channel Sync/Async Serial Port  Interface Card,3*1
					 bnameSU113GWC(16719896),          --SRG20,SU113GWC,3G-WCDMA Service Board,3*1
					 bnameSU113GCD(16719897),          --SRG20,SU113GCD,3G-CDMA2000 Service Board,3*1
					 bnameSU113GTD(16719898),          --SRG20,SU113GTD,3G-TD-SCDMA Service Board,3*1
					 bnameSU11E5FE(16719899),          --SRG20,SU11E5FE,5-Port Fast Ethernet Switch Electrical Interface Board(RJ45),3*1
					 bnameFWF1SPUA(16719900),          --FWF1SPUA,Main Process Unit Board,1*1  USG2100
					 bnameFWF1SPUB(16719901),          --FWF1SPUB,Main Process Unit Board,1*1  USG2100
					 bnameFWF1MPUD(16719902),          --FWF1MPUD,Main Process Unit Board,1*1  USG2100
					 bnameFWF1MPUC(16719903),          --FWF1MPUC,Main Process Unit Board,1*1  USG2100
					 bnameSU11ADPAO2(16719904),          --SU11ADPA,Main Process Unit Board,1*1  USG2100  duplicated with bnameSU11ADPA(16719932), add 'O2'
					 bnameSU11F8E1(16719905),          --SRG20,SU11F8E1,8-port E1 Interface Card-DB44-75ohm,1*1
					 bnameSU11FC8E1(16719906),         --SRG20,SU11FC8E1,8-port Channelized E1 Interface Card-DB44-75ohm,1*1
					 bnameSU11F4E1(16719907),          --SRG20,SU11F4E1,4-port E1 Interface Card-DB44-75ohm,1*1
					 bnameSU11FC4E1(16719908),         --SRG20,SU11FC4E1,4-port Channelized E1 Interface Card-DB44-75ohm,1*1
					 bnameSU11APWN(16719909),          --SRG20,SU11APWN,WLAN Service Board,3*1
					 bnameSU21MPUA(16719910),          --USG5100,SU21MPUA,Main Process Unit Board,1*1
					 bnameSU11MPUA(16719911),          --USG5100,SU11MPUA,Main Process Unit Board,1*1
					 bnameFWE1E4GE(16719912),          --USG5100,FWE1E4GE,4-port Gigabit Ethernet Interface Card(RJ45),1*1
					 bnameFWG1F2F2C(16719913),         --USG2200,FWG1F2F2C,2FE(RJ45)+2FE(RJ45&SFP) MIXED INTERFACE CARD,1*1
					 bnameSU21F18S2(16719914),         --USG5100,SU21F18S2,18FE(RJ45)+2GE(SFP) Mixed Interface Card ,1*1
					 bnameSU21G16S4(16719915),         --USG5100,SU21G16S4,16GE(RJ45)+4GE(SFP) Mixed Interface Card  ,1*1
					 bnameSU11E8F2G(16719916),         --SRG20,SU11E8F2G,8FE(RJ45)+2GE(RJ45) Mixed Interface Card,3*1
					 bnameSRGM1WCDMA(16719917),        --SRG,SRGM1WCDMA,USB 3G WCDMA Card
					 bnameSRGM1CD2K(16719918),         --SRG,SRGM1CD2K,USB 3G CDMA2000
					 bnameSRGM1TD(16719919),           --SRG,SRGM1TD,USB 3G TDSCDMA
					 bnameSU11X86HS02(16719920),       --Safety Product,USG2200,SU11X86HS02,Enhanced Services Platform Enterprise Version,
																  -- X86 Board,CPU T7500,2GB Memory,160G Enterprise Hard Disk
					 bnameSU11X86HS01(16719921),       --Safety Product,USG2200,SU11X86HS01,Enhanced Services Platform Common Version,
																  -- X86 Board,CPU T7500,2GB Memory,160G Universal Hard Disk
					 bnameSU01MPUA(16719922),          -- SRG20,SU01MPUA,SRG20  Main Processing Unit ,2*1
					 bnameSU01MPUB(16719923),          -- SRG20,SU01MPUB,SRG20  Main Processing Unit ,2*1
					 bnameSU01MPUC(16719924),          -- SRG20,SU01MPUC,SRG20  Main Processing Unit ,2*1
					 bnameSU01ADPA(16719925),          -- SRG20,SU01ADPA,ADSL2+Multi-PVCs,2*2
					 bnameSU11SMX01(16719926),         -- Safety Product,SRG20,SU11SMX01,Enhanced Services Platform,ultra-low-end ,with CF Card, no Hard Disk
					 bnameSU11DMX02(16719927),         -- Safety Product,SRG20,SU11DMX02,Enhanced Services Platform,low-end , 2.5'' Hard Disk
					 bnameSU11DFX03(16719928),         -- Safety Product,SRG20,SU11DFX03, Enhanced Services Platform,mid-range , 2.5'' Hard Disk
					 bnameSU11DFX04(16719929),         -- Safety Product,SRG20,SU11DFX04, Enhanced Services Platform,mid-range , two 2.5'' Hard Disk
					 bnameSU11DFX05(16719930),         -- Safety Product,SRG20,SU11DFX05, Enhanced Services Platform,high-end ,with CF Card, two 2.5'' Hard Disk
					 bnameFWG2MPUA(16719931),          -- USG2200,FWG2MPUA,Main Process Unit Board,1*1
					 bnameSU11ADPA(16719932),          -- SRG20,SU11ADPA,ADSL2+Multi-PVCs,with HS General Security Platform Software,1*1
					 bnameFWF1E1FEO(16719933),          -- USG2100,FWF1E1FE,1-Port Fast Ethernet Electrical Interface Board(RJ45),3*1  duplicated with bnameFWF1E1FE(16719877) add 'O'
					 bnameSU11EPSEC(16719934),         -- USG5100,SU11EPSEC,High Speed IPsec Card,with HS General Security Platform Software
					 bnameSU51E4BYO(16719935),          -- USG5100,SU51E4BY,4GE Electric Ports Bypass Card,with HS General Security Platform Software,1*1  duplicated with bnameSU51E4BY(16719960) add 'O'
--USG3000/USG50/USG5000/SVN
					 bnameRTB21CT1(16719950),          --USG3000,RTB21CT1,1-port T1&Fractional T1 Interface Card,1*1
					 bnameRRTB21CE1(16719951),         --USG3000,RTB21CE1,1-port CE1&Fractional CE1 Interface Card,1*1
					 bnameRTB21T1(16719952),           --USG3000,RTB21T1,1-port T1&Fractional T1 Interface Card,1*1
					 bnameRTB21E1(16719953),           --USG3000,RTB21E1,1-port E1&Fractional E1 Interface Card,1*1
					 bnameSE21MPUA(16719954),           --SVN5300,Security virtual Gateway Mainboard(4GE)
					 bnameWCDMA(16719955),             --SVN5300,Security 3G board(WCDMA)
					 bnameTD-SCDMA(16719956),          --SVN5300,Security 3G board(TD-SCDMA)
					 bnameCDMA2000(16719957),          --SVN5300,Security 3G board(CDMA2000)
					 bnameSU51MPUB(16719958),          --USG5500,SU51MPUB,1U Main Processing Unit,1*1
					 bnameSU51SACCO(16719959),          --USG5500,SU51SACC,Service Accelerate Card,1*1  duplicated with bnameSU51SACC(16719967) add 'O'
					 bnameSU51E4BY(16719960),          --USG5500,SU51E4BY,4GE Electric Ports Bypass Card,with HS General Security Platform Software,1*1
					 bnameSU51MPUA(16719961),          --USG5500,SU51MPUA,Main Processing Unit,1*1
					 bnameSU51X2G8(16719962),          --USG5500,SU51X2G8,2*10GE Optical Ports+8GE Electric Ports Interface Card,with HS General Security Platform Software,1*1
					 bnameSU51E2XSM(16719963),         --USG5500,SU51E2XSM,2*10GE Optical Ports Interface Card,with HS General Security Platform Software,3*1
					 bnameSU51E8GF(16719964),          --USG5500,SU51E8GF,8GE Optical Ports Interface Card,with HS General Security Platform Software,2*1
					 bnameSU51E8GE(16719965),          --USG5500,SU51E8GE,8GE Electric Ports Interface Card,with HS General Security Platform Software,1*1
					 bnameSU51E2XSF(16719966),         --USG5500,SU51E2XSF,2*10GE Optical Ports Interface Card,with HS General Security Platform Software,1*1
					 bnameSU51SACC(16719967),          --USG5500,SU51SACC,Service Accelerate Card,1*1
					 bnameSU51F2BY(16719968),          --USG5500,2 Link LC/UPC Optical Interface Bypass Protect Card
					 bnameSU51E8GFF(16719969),         --USG5500,8GE Optical Ports FIC Interface Card
					 bnameSU71DFX01(16719970),         --Safety Product,NIP5100,SU71DFX01,Enhanced Services Platform,High-end,for IPS
					 bnameSU51ESPA(16719971),          --NIP5100,ESP,SU51ESPA,X86 Process Card,1*1
					 bnameSU51ESPC(16719972),          --NIP5100,ESP,SU51ESPC,IPS Process Card,1*1
					 bnameSU51F2BY01(16719973),        --USG5500,SU51F2BY01,2 Link LC/UPC Multimode Optical Interface Bypass Protect Card,with HS General Security Platform Software
					 bnameSU51F2BY02(16719974),        --USG5500,SU51F2BY02,2 Link LC/UPC Singlemode Optical Interface Bypass Protect Card,with HS General Security Platform Software
					 bnameSUA1CPUA(16719975),          --Eudemon1000E-N CPU Card
					 bnameSUA2MPUA(16719976),          --USG6600 Main Processing Unit
					 bnameSUA2CSPUA(16719977),         --USG6600 Content Security Process Unit
					 bnameSUA2X2G8(16719978),          --USG6600 2*10GE Optical Ports+8GE Electric Ports Interface Card
					 bnameSUA2E2XSF(16719979),         --USG6600 2*10GE Optical Ports Interface Card
					 bnameSUE3E8GF(16719980),          --USG6600 8GE Optical Ports Interface Card
					 bnameSUE3E4BY(16719981),          --USG6600 4GE Electric Ports Bypass Card
					 bnameSUE3E8GE(16719982),          --USG6600 8GE Electric Ports Interface Card
					 bnameSUE5MPUA(16719983),          -- USG3600 Main Processing Unit
					 bnameSUE5DSBB(16719984),          -- USG3600 HD Switch Board
					 bnameSUA1MPUB(16719985),          -- USG3600 1U Main Processing Unit Board
					 bnameSUE1EPSEC(16719986),         -- USG3600 The state password encryption Daughter card
					 bnameSUE5FIBA(16719987),	  --Fixed Interface Board
					 bnameET1D2IPS0S002(16719988),	  -- IPS Module A,with HW General Security Platform Software
					 bnameET1D2FW00S002(16719989),	  -- NGFW Module A,with HW General Security Platform Software
					 bnameET1D2FW00S012(16719990),	  -- NGFW Module B,with HW General Security Platform Software
					 bnameET1D2FW00S022(16719991),	  -- NGFW Module C,with HW General Security Platform Software
					 bnameLE1D2FW00S012(16719992),	  -- NGFW Module B,with HW General Security Platform Software
					 bnameSUE6MPUA(16719993),	  -- Manufactured Board,USG6600,SUE6MPUA,Main Processing Unit Board
					 bnameSUE3MPUA(16719994),	  -- Manufactured Board,USG6300,SUE3MPUA,Main Processing Unit Board
					 bnameSUE3BPKA(16719995),	  -- USG6300,SUE3BKPA,1U BackPlane Board

--SIG9800 Serie's TC-MIB vlaue scope:   16732160 ~ 16736255  or Hex format:0x00ff5000~0x00ff5fff    (Both 16732160 and 16736255 are included)
--SIG9800
					 bnameSIG9800SPUA(16732160),          --SPUA Board
					 bnameSIG9800SFUG(16732161),          --160G SFUG
					 bnameSIG9800IG21SPUC02(16732162),    --40G X3 Service Processing Unit,with HS Service Inspection Gateway Software
					 bnameSIG9800IG21SPUD02(16732163),    --40G X8&X16 Service Processing Unit,with HS Service Inspection Gateway Software
					 bnameSIG9800IG2D00E1NS00(16732164),  --SIG9800-X,IG21E1NC00,1-Port 100GBase-CFP Integrated Line Processing Unit (LPUI-101)
					 bnameSIG9800IG2DLPUFA000(16732165),  --SIG9800-X,IG21LPUF100CA00,Flexible Card Line Processing Unit(LPUF-101)
					 bnameSIG9800IG21LPUF120A00(16732166),  --SIG9800-X,IG21LPUF120A00,Flexible Card Line Processing Unit(LPUF-120),with HW Service Inspection Gateway Software
					 bnameSIG9800IG21LPUF240A00(16732167),  --SIG9800-X,IG21LPUF240A00,Flexible Card Line Processing Unit(LPUF-240),with HW Service Inspection Gateway Software
					 bnameSIG9800IG21MPUD2(16732168),  --SIG9800-X,IG21MPUD2,X3 Main Processing Unit D2(Including 2G Memory and 2G USB),with HW Service Inspection Gateway Software


--Eudemon8000E/USG9000 Serie's TC-MIB vlaue scope:    16748544 ~ 16752639  or Hex format:0x00ff9000 ~ 0x00ff9fff    (Both 16748544 and 16752639 are included)
--Eudemon8000E/USG9000
					 bnameE8000EKW51ESPU(16748544),        --SPU Board ,Service Processing Unit
					 bnameE8000EDCU(16748545),         --DCU Board ,Detection and Clean Unit
					 bnameE8000ESUP3SPUA02(16748546),          --Service Processing Unit,with HS General Security Platform Software
					 bnameE8000ECR52LPUKD1(16748547),     --Flexible Card Line Processing Unit(LPUF-21,2 sub-slots) B
					 bnameE8000ESUP3SPUA02IPS(16748548),  --IPS Service Processing Unit,with HS General Security Platform Software
					 bnameE8000EKW51ESPUIPS(16748549),      --IPS SPU Board ,Service Processing Unit
		bnameE8000ESU91SPUC(16748550),      --Eudemon8000E-X,SU91SPUC,X3 Service Processiong Unit(Base Board),with HS General Security Platform Software
		bnameE8000ESU91SPUD(16748551),      --Eudemon8000E-X,SU91SPUD,X8&X16 Service Processiong Unit(Base Board),with HS General Security Platform Software

		bnameE8000ESU91SPUC01(16748552),    --Eudemon8000E-X,SU91SPUC01,40G X3 Firewall Service Processing Unit ,with HW General Security Platform Software,include SPUC and 1*SPCC01
		bnameE8000ESU91SPUC02(16748553),    --Eudemon8000E-X,SU91SPUC02,20G X3 Firewall Service Processing Unit(oversea),with HW General Security Platform Software,include SPUC and 1*SPCB02
		bnameE8000ESU91SPUC03(16748554),    --Eudemon8000E-X,SU91SPUC03,60G X3 Firewall Service Processing Unit ,with HW General Security Platform Software
		bnameE8000ESU91SPUD01(16748555),    --Eudemon8000E-X,SU91SPUD01,40G X8&X16 Firewall Service Processing Unit ,with HW General Security Platform Software,include SPUD and  1*SPCC01
		bnameE8000ESU91SPUD02(16748556),    --Eudemon8000E-X,SU91SPUD02,80G X8&X16 Firewall Service Processiong Unit,with HW General Security Platform Software,include SPUD and 1*SPCB01
		bnameE8000ESU91SPUD03(16748557),    --Eudemon8000E-X,SU91SPUD03,20G X8&X16 Firewall Service Processing Unit(oversea),with HW General Security Platform Software,include SPUD and 1*SPCB02

		bnameE8000ESU91SPUC04(16748570),    --Eudemon8000E-X,SU91SPUC04,40G X3 Firewall Service Processing Unit ,Double CPUs,with HW General Security Platform Software,include SPUC and 1*SPCB04
					 bnameE8000ESU91SPUD05(16748571),    --Eudemon8000E-X,SU91SPUD05,40G X8&X16 Firewall Service Processing Unit ,Double CPUs,with HW General Security Platform Software,include SPUD and  1*SPCB04
					 bnameE8000ESU91LPUF100CA00(16748572),	--Eudemon8000E-X,SU91LPUF100CA00,Flexible Card Line Processing Unit(LPUF-101,4 sub-slots),with HW General Security Platform Software
					 bnameE8000ESU91LPUF100CA0(16748573),	--Eudemon8000E-X3,SU91LPUF100CA01,X3 Flexible Card Line Processing Unit(LPUF-100,4 sub-slots),with HW General Security Platform Software
					 bnameE8000ESU91LPUI100CA00(16748574),	--Eudemon8000E-X,SU91LPUI100CA00,10-Port 10GBase LAN/WAN-SFP+ Integrated Line Processing Unit (LPUI-100) ,with HW General Security Platform Software
					 bnameE8000ESU91E1NC00(16748575),	--Eudemon8000E-X,SU91E1NC00,1-Port 100GBase-CFP Integrated Line Processing Unit (LPUI-101),with HW General Security Platform Software
					 bnameEudemon8000ESU91EDXFB0(16748576),	--Eudemon8000E-X,SU91EDXFB0,16-Port 10GBase LAN-SFP+ Integrated Line Processing Unit (LPUI-100) ,with HW General Security Platform Software
					 bnameEudemon8000ESU91E4XFA0(16748577),	--Eudemon8000E-X,SU91E4XFA0,4-Port 10GBase LAN-SFP+ Flexible Card(P100,1/4wide,Occupy one sub-slots)
					 bnameEudemon8000ESU91LBXF0(16748578),	--Eudemon8000E-X,SU91LBXF0,12-Port 10G Base LAN/WAN-SFP+ Flexible Card A(P120-A)


-- USG9100 Board/Card :
					 bnameUSG9100SU61SPUA(16748552),     -- Service Processing Board,with HS General Security Platform Software
					 bnameUSG9100SU61E8GF(16748553),     -- 8-port GE Optical Interface Card(SFP),with HS General Security Platform Software
					 bnameUSG9100SU61P4UF(16748554),     -- 4-port 2.5G POS Optical Interface Card (SFP),with HS General Security Platform Software
					 bnameUSG9100SU61E1XX(16748555),     -- 1-port 10G LAN XFP Optical Interface Board,with HS General Security Platform Software
					 bnameUSG9100SU61W1XX(16748556),     -- 1-port 10G WAN XFP Optical Interface Board,with HS General Security Platform Software
					 bnameUSG9100SU61P1XX(16748557),     -- 1-port 10G POS XFP Optical Interface Board,with HS General Security Platform Software
					 bnameUSG9100SU61MSU01(16748558),    -- ATCA Main Processing & Switching Unit,with HS General Security Platform Software
					 bnameUSG9100SU61SMMD02(16748559),   -- Shelf Management Module,with HS General Security Platform Software
					 bnameUSG9100SU6Z1ATCA(16748560),    -- Integrated Chassis Components-5U
					 bnameUSG9100SU6Z2ATCA(16748561),    -- Integrated Chassis Components-14U
					 bnameUSG9100CN6E01FFB(16748562),    -- CGA Integrated Frame Fan Box
					 bnameUSG9100CN6E02FFB(16748563),    -- 5U Integrated Frame Fan Box


--Security Product's TC-MIB end


-- Virtual board of Net Management: from 0X70000000
					 bnameMDUUNKNOWN(1879048192),             -- Virtual remote board of type unknown
					 bnameMDUMA5620E(1879048193),             -- Virtual remote board of MA5620E
					 bnameMDUMA5626E(1879048194),             -- Virtual remote board of MA5626E

-- END
					 bnameEND(2147483647)            -- End

					 }

		  HWSubPCBType ::= TEXTUAL-CONVENTION
				STATUS current
				DESCRIPTION
					 "This data type is used as the syntax of the
					 hwSubslotType object in the definition of
					 HUAWEI-DEVICE-MIB's hwSubslotTable.

					 The definition of this textual convention with the
					 addition of newly assigned values is published
					 periodically by the Huawei MIB Criterion Group, every
					 value indicate a SubPCB produced by Huawei.
					 "
				SYNTAX INTEGER
					 {
					 subbnameunknown(1),
					 subbnameh511o2ctg(2),           -- Subboard that provides two 155M ATM ports (single-mode 30 km), which is used for MA
					 subbnameh511o2ctb(3),           -- Subboard that provides two 155M ATM ports (multi-mode 2 km), which is used for MA
					 subbnameh511o1ctg(4),           -- Subboard that provides one 155M ATM port (single-mode 30 km), which is used for MA
					 subbnameh511o1ctb(5),           -- Subboard that provides one 155M ATM port (multi-mode 2 km), which is used for MA
					 subbnameh511v2ht(6),            -- ARC subboard, which provides two 622M single-mode optical ports
					 subbnameh511v1ht(7),            -- ARC subboard, which provides one 622M single-mode optical port and one electric port
					 subbnameh512o8ffb(8),           -- Subboard that provides eight 100M Ethernet optical ports (multi-mode 2 km)
					 subbnameh512o8fff(9),           -- Subboard that provides eight 100M Ethernet optical ports (single-mode 15 km)
					 subbnameh511o1gfa(10),          -- Subboard that provides one GE optical port (multi-mode 500 m)
					 subbnameh511o1gfe(11),          -- Unavailable
					 subbnameh511o1gfg(12),          -- Unavailable
					 subbnameh511o2cpb(13),          -- ATM subboard that provides two STM-1 optical ports (multi-mode, 2 km),which is used for MD
					 subbnameh511o2cpg(14),          -- ATM subboard that provides two STM-1 optical ports (single-mode, 30 km), which is used for MD
					 subbnameh511o1cpb(15),          -- ATM subboard that provides one STM-1 optical port (multi-mode, 2 km), which is used for MD
					 subbnameh511o1cpg(16),          -- ATM subboard that provides one STM-1 optical port (single-mode, 30 km), which is used for MD
					 subbnameh511o1hxc(17),          -- ATM subboard that provides one STM-4 optical port (single-mode, long-distance)
					 subbnameh511o1hxb(18),          -- ATM subboard that provides one STM-4 optical port (single-mode, medium-distance)
					 subbnameh511o1hxa(19),          -- ATM subboard that provides one STM-4 optical port (multi-mode, short-distance)
					 subbnameh511e23t(20),           -- Subboard that provides two E3 ATM electric ports
					 subbnameh511e13t(21),           -- Subboard that provides one E3 ATM electric port
					 subbnameh511t23t(22),           -- Subboard that provides two T3 ATM electric ports
					 subbnameh511t13t(23),           -- Subboard that provides one T3 ATM electric port
					 subbnameh511o2cvb(24),          -- SDH subboard that provides two STM-1 optical ports (multi-mode 2 km)
					 subbnameh511o2cvg(25),          -- SDH subboard that provides two STM-1 optical ports (single-mode, 30 km)
					 subbnameh511e8it(26),           -- 8-port IMA subboard
					 subbnameh511e81d(27),           -- 8-port E1 subboard
					 subbnameh511e8vd(28),           -- 8-port V35 subboard
					 subbnameh511s81d(29),           -- 8-port G.SHDSL subboard
					 subbnamevc01sdsp(30),           -- VSP subboard

-- 20020619 New
					 subbnameh511o1gfx(31),          -- Subboard that provides one GE optical port (single-mode 10 km)
					 subbnameh511e8fi(32),           -- E8FI: subboard that provides 8 10M/100M Ethernet electric ports
					 subbnameh511o1cvb(33),          -- SDH subboard that provides one STM-1 optical port (multi-mode, 2 km)
					 subbnameh511o1cvg(34),          -- SDH subboard that provides one STM-1 optical port (single-mode, 30 km)

-- New IMA subboards of the UA3000
					 subbnameh601e8ia(35),           -- Subboard that provides eight IMA E1 electric ports
					 subbnameh601o1cng(36),          -- Subboard that provides one 155M, ATM, single-mode, and 30 km optical port (SC)
					 subbnameh601o1cnb(37),          -- Subboard that provides one 155M, ATM, multi-mode, and 2 km optical port (SC)
					 subbnameh601o2cng(38),          -- Subboard that provides two 155M, ATM, single-mode, and 30 km optical ports (SC)
					 subbnameh601o2cnb(39),          -- Subboard that provides two 155M, ATM, multi-mode, and 2 km optical ports (SC)
																-- New subboards of the IAS
					 subbnameh511e1ct(40),           -- Subboard that provides one 155M ATM electric port
					 subbnameh511e2ct(41),           -- Subboard that provides two 155M ATM electric ports
					 subbnameh531o1gaa(42),          -- Subboard that provides one GE multi-mode optical port
					 subbnameh531o2gaa(43),          -- Subboard that provides two GE multi-mode optical ports
					 subbnameh531o1gae(44),          -- Subboard that provides one GE single-mode optical port
					 subbnameh531o2gae(45),          -- Subboard that provides two GE multi-mode optical ports
					 subbnameh531e4fb(46),           -- Subboard that provides four 10M/100M Ethernet electric ports-for BASE
					 subbnameh53104fbf(47),          -- Subboard that provides four 10M/100M Ethernet optical ports (single-mode 15 km, LC interface)-for BASA and BASE
					 subbnameh53104fbb(48),          -- Subboard that provides four 10M/100M Ethernet optical ports (multi-mode 2 km, LC interface)-for BASA and BASE
-- MA5200
					 subbnameaim1(50),
					 subbnameaim2(51),
					 subbnameaim3(52),
					 subbnameaim4(53),
					 subbnamepim1(54),
					 subbnamepim2(55),
					 subbnamepim3(56),
					 subbnamepim4(57),
					 subbnameh521E6FC(58),           -- 6-channel electric interface Subboard of speediness Ethernet
					 subbnameh521O6FCSMTRJ(59),      -- Single-mode 6-channel MTRJ optical interface Subboard of speediness Ethernet
					 subbnameh521O6FCMMTRJ(60),      -- Multi-mode 6-channel MTRJ optical interface Subboard of speediness Ethernet
					 subbnameh521O6FCSLC(61),        -- Single-mode 6-channel LC optical interface of speediness Ethernet
					 subbnameh521O1GCSMTRJ(62),      -- Single-mode 1-channel Gigabit MTRJ optical interface Subboard of speediness Ethernet
					 subbnameh521O1GCMMTRJ(63),      -- Multi-mode 1-channel Gigabit MTRJ optical interface Subboard of speediness Ethernet
					 subbnameh521O1GCSLC(64),        -- Single-mode 1-channel Gigabit LC optical interface Subboard of speediness Ethernet
					 subbnameh521O1GCMLC(65),        -- Multi-mode 1-channel Gigabit LC optical interface Subboard of speediness Ethernet
					 subbnameh521O2GCSMTRJ(66),      -- Single-mode 2-channel Gigabit MTRJ optical interface Subboard of speediness Ethernet
					 subbnameh521O2GCMMTRJ(67),      -- Multi-mode 2-channel Gigabit MTRJ optical interface Subboard of speediness Ethernet
					 subbnameh521O2GCSLC(68),        -- Single-mode 2-channel Gigabit LC optical interface Subboard of speediness Ethernet
					 subbnameh521O2GCMLC(69),        -- Multi-mode 2-channel Gigabit LC optical interface Subboard of speediness Ethernet
					 subbnameh521EGCSTKC(70),        -- Gigabit electric interface piling Subboard of Ethernet
					 subbnameh521OGCSTKC(71),        -- Gigabit electric interface piling Subboard of Ethernet
					 subbnameh521P1CCOC3(72),        -- 155M POS Subboard
					 subbnameh521P1HCOC12(73),       -- 622M POS Subboard
-- ESR SubCard Type
					 subbnameAtm155(130) ,           -- Include ATM155 and ATM155A.
					 subbnameAtm622(131) ,           -- Include ATM622 and ATMA622.
					 subbnamePos155 (132) ,          -- ESR not support by now, reserved for future.
					 subbnamePos622(133) ,           -- BS22P2HA
					 subbnameO2cc   (134) ,          -- Board subCard of CES(Circuit Emluator System ),Serial number:BS22O2CC
					 subbnameE43a(135) ,             -- Realize ATM accessing of E3,Serial number:BS21E43A
					 subbnameE8fi (136) ,            -- SN01E8FI
					 subbnameO8fi (137) ,            -- SN01O8FI
					 subbnameO1gi (138) ,            -- SN01O1GI
					 subbnameE8f(139),               -- BS22E8FA/BS22E8FB electric port FE subcard   BS22LPUD subcard
					 subbnameO8f (140) ,             -- BS22O8FA/BS22O8FB optical port FE subcard   BS22LPUD subcard
					 subbnameO1g (141) ,             -- BS22O1GA,                        BS22LPUC subcard
					 subbnameO2g (142) ,             -- BS22O2GA,BS22O2GB                BS22LPUC subcard
					 subbnameO8g (143) ,             -- BS22O8GA                         BS22LPUC subcard
					 subbnameAtm2g5(144) ,           -- Subboard that provides the 2.5G ATM access and can be inserted only in the LPUB.
																-- Its number is BS22O1SC (BS22LPUB subcard).
					 subbnameBfm(145),               -- BS22BFMA, based on 01G; BS22BFMB, based on 02G
					 subbnameh601e23a(146),          -- Subboard that provides two E3 ATM electric ports
					 subbnameh601e13a(147),          -- Subboard that provides one E3 ATM electric port
-- New subboards for the LAND board
					 subbnameH511o1GTG(148),         -- Subboard that provides one 1000M optical port (single-mode, 40 km, 1550nm) for the LAND board
-- VPRING subboards
					 subbnameh511v2htg(151),         -- H511V2HTG VPRING subboard that provides two 622M optical ports (single-mode, 40 km, and SC interface)
					 subbnameh511v1htg(152),         -- H511V1HTG VPRING subboard that provides one 622M optical port (single-mode, 40 km, SC interface)
					 subbnameh511v2htb(153),         -- H511V2HTB VPRING subboard that provides two 622M optical ports (multi-mode, 2 km, and SC interface)
					 subbnameh511v1htb(154),         -- H511V1HTB VPRING subboard that provides one 622M optical port (multi-mode, 2 km, and SC interface)
					 subbnameh601v2haf(155),         -- H601V2HAF VPRING subboard that provides two 622M optical ports (single-mode, 15 km, and SC interface)
					 subbnameh601v1haf(156),         -- H601V1HAF VPRING subboard that provides one 622M optical port (single-mode, 15 km, and SC interface)
					 subbnameh601v2hag(157),         -- H601V2HAG VPRING subboard that provides two 622MM optical ports (single-mode, 40 km, and SC interface)
					 subbnameh601v1hag(158),         -- H601V1HAG VPRING subboard that provides one 622M optical port (single-mode, 40 km, and SC interface)
					 subbnameh601v2hab(159),         -- H601V2HAB VPRING subboard that provides two 622M optical ports (multi-mode, 2 km, and SC interface)
					 subbnameh601v1hab(160),         -- H601V1HAB VPRING subboard that provides one 622M optical port (multi-mode, 2 km, and SC interface)
					 subbnameh601cesa(165),          -- Subboard that provides eight IMA El electric ports
					 subbnameh601v2ha(166),          -- Subboard that provides one 155M ATM optical port (single-mode, 30 km, and SC interface) //to be aborted
-- Subboards for the LAND board
					 subbnameLande8fs(167),
					 subbnameLando8fsb(168),
					 subbnameLando8fsf(169),
					 subbnameLando8fsg(170),
					 subbnameLando4fsb(171),
					 subbnameLando4fsf(172),
					 subbnameLando4fsg(173),
					 subbnameLando1gta(174),
					 subbnameLando1gtf(175),
					 subbnameLando1gth(176),
					 subbnameh512e81d(177),
					 subbnameLando2fsb(178),         -- Subboard that provides two 100M optical ports (multi-mode)
					 subbnameLando2fsf(179),         -- Subboard that provides two 100M optical ports (single-mode, 15 km, and 1310 nm)
					 subbnameLando2fsg(180),         -- Subboard that provides two 100M optical ports (single-mode, 40 km, and 1310 nm)
					 subbnameLando1fsb(181),         -- Subboard that provides one 100M optical port (multi-mode)
					 subbnameLando1fsf(182),         -- Subboard that provides one 100M optical port (single-mode, 15 km, and 1310 nm)
					 subbnameLando1fsg(183),         -- Subboard that provides one 100M optical port (single-mode, 40 km, and 1310 nm)
-- 622M ATM subboard
					 subbnamebs22o1hda(184),         -- ATM subboard that is based on the SD537 chipset and provides one 622M optical port (multi-mode, 0.5 km)
					 subbnamebs22o1hdb(185),         -- ATM subboard that is based on the SD537 chipset and provides one 622M optical port
																-- (single-mode, medium-distance, 15 km)
					 subbnamebs22o1hdc(186),         -- ATM subboard that is based on the SD537 chipset and provides one 622M optical port
																-- (single-mode, long-distance, and 40 km)
					 subbnameH601e2fn(187),          -- Subboard that provides two 10M/100M Ethernet electric ports
					 subbnameH601o2fnf(188),         -- Subboard that provides two 10M/100M Ethernet optical ports (single-mode, 15 km, 1310 nm, and LC interface)
					 subbnameH601o2fnb(189),         -- Subboard that provides two 10M/100M Ethernet optical ports (multi-mode, 2 km, 1310 nm, and LC interface)
					 subbnameH601o1fnf(190),         -- Subboard that provides one 10M/100M Ethernet optical port (single-mode, 15 km, 1310 nm, and LC interface)
					 subbnameH601o1fnb(191),         -- Subboard that provides one 10M/100M Ethernet optical port (multi-mode, 2 km, 1310 nm, and LC interface)
					 subbnameH601o1gne(192),         -- Subboard that provides one GE optical port (single-mode, 10 km, 1310 nm, and LC interface)
					 subbnameH601o1gna(193),         -- Subboard that provides one GE optical port (multi-mode, 500 m, 850 nm, and LC interface)
					 subbnameH601o1gng(194),         -- Subboard that provides one GE optical port (single-mode, 40 km, 1510 nm, and LC interface)
-- VPU subboards
					 subbnamevpuh511etca(195),       -- VPU DSP 160-channel subboard
					 subbnamevpuh511etcb(196),       -- VPU DSP 600-channel subboard
					 subbnamevpuh511e2fn(197),       -- Subboard for the VPU board. This subboard provides two FE electric ports.
					 subbnamevpuh511o2fnb(198),      -- Subboard for the VPU board. This subboard provides two FE optical ports.
					 subbnamevpuh511o1gna(199),      -- Subboard for the VPU board. This subboard provides the FE electric port and the GE port.
-- Subboards for the MSUC board
					 subbnameH511O1CSB(200),         -- Subboard for the MSUC board. This subboard provides one 155M optical port (SDH, multi-mode, and 2 km).
					 subbnameH511O1CSF(201),         -- Subboard for the MSUC board. This subboard provides one 155M optical port (SDH, single-mode, and 15 km).
					 subbnameH511O1CSG(202),         -- Subboard for the MSUC board. This subboard provides one 155M optical port (SDH, single-mode, and 40 km).
					 subbnameH511E1CS(203),          -- Subboard for the MSUC board. This subboard provides one 155M SDH electric port.

-- Subboards for the VPU board
					 subbnamevpuh511e1fn(204),       -- Subboard for the VPU board. This subboard provides one 10M/100M Ethernet electric port.
					 subbnamevpuh511o2fnf(205),      -- Subboard for the VPU board. This subboard provides two 100M Ethernet optical ports (single-mode, 15 km).
					 subbnamevpuh511o1fnb(206),      -- Subboard for the VPU board. This subboard provides one 100M Ethernet optical port (multi-mode, 2 km).
					 subbnamevpuh511o1fnf(207),      -- Subboard for the VPU board. This subboard provides one 100M Ethernet optical port (single-mode, 15 km).
					 subbnamevpuh511o1gne(208),      -- Subboard for the VPU board. This subboard provides one 1000M Ethernet optical port (single-mode, 10 km).
					 subbnamevpuh511o1gng(209),      -- Subboard for the VPU board. This subboard provides one 1000M Ethernet optical port (single-mode, 40 km).

-- 155M ATM optical subboards
					 subbnameH601O2CNH(210),         -- UA subboard H601O2CNH, which provides two 155M ATM optical ports (single-mode, 60 km)
					 subbnameH601O1CNH(211),         -- UA subboard H601O1CNH, which provides one 155M optical port (single-mode, 60 km)
					 subbnameH511O2CPH(212),         -- Subboard H511O2CPH, which provides two 155M optical ports (single-mode, 60 km)
					 subbnameH511O1CPH(213),         -- Subboard H511O1CPH, which provides one 155M optical port (single-mode, 60 km)
					 subbnameH511O2CPI(214),         -- Subboard H511O2CPI, which provides two 155M optical ports (single-mode, 90 km)
-- UA VPRING subboards
					 subbnameH602V2HAF(215),         -- VPRING subboard H602V2HAF, which provides two 622M optical ports (single-mode, 15 km, SC interface, and SD537 chipset)
					 subbnameH602V1HAF(220),         -- VPRING subboard H602V1HAF, which provides one 622M optical port (single-mode, 15 km, SC interface, and SD537 chipset)
					 subbnameH602V2HAG(221),         -- VPRING subboard H602V2HAG, which provides two 622M optical ports (single-mode, 40 km, SC interface, and SD537 chipset)
					 subbnameH602V1HAG(222),         -- VPRING subboard H602V1HAG, which provides one 622M optical port (single-mode, 40 km, SC interface, and SD537 chipset)
					 subbnameH602V1HTF(223),         -- VPRING subboard H602V1HTF, which provides one 622M optical port (single-mode, 15 km, SC interface,
																-- SD537 chipset, and interconnected electric ports)
					 subbnameH602V1HTG(224),         -- VPRING subboard H602V1HTG, which provides one 622M optical port (single-mode, 40 km, SC interface,
																-- SD537 chipset, and interconnected electric ports)

					 subbnameH602V2HCF(225),         -- VPRING subboard H602V2HCF, which provides two 622M optical ports
																-- (single-mode, 15 km, SC interface, stratum-3 clock, and SD537 chipset)
					 subbnameH602V1HCF(226),         -- VPRING subboard H602V1HCF, which provides one 622M optical port
																-- (single-mode, 15 km, SC interface, stratum-3 clock, and SD537 chipset)
					 subbnameH602V2HCG(227),         -- VPRING subboard H602V2HCG, which provides two 622M optical ports
																-- (single-mode, 40 km, SC interface, SD537 chipset, and stratum-3 clock)
					 subbnameH602V1HCG(228),         -- VPRING subboard H602V1HCG, which provides one 622M optical port
																-- (single-mode, 40 km, SC interface, SD537 chipset, and stratum-3 clock)
					 subbnameH602V1HEF(229),         -- VPRING subboard H602V1HEF, which provides one 622M optical port
																-- (single-mode, 15 km, SC interface, SD537 chipset, interconnected electric ports, and stratum-3 clock)
					 subbnameH602V1HEG(230),         -- VPRING subboard H602V1HEG, which provides one 622M optical port
																-- (single-mode, 40 km, SC interface, SD537 chipset, interconnected electric ports, and stratum-3 clock)


-- 8070
					 subbnameRTC1ETPA(300),          -- Ethernet process card
					 subbnameRTC1ETKA(301),          -- Ethernet back card
					 subbnameRTC1ETKX(302),          -- Ethernet back card(fiber)
					 subbnameRTC1GEM(303),           -- GE process card(fiber)
					 subbnameRTC1GEPA(304),          -- GE process card
					 subbnameRTC1GEKA(305),          -- GE back card(A)
					 subbnameRTC1GEKB(306),          -- GE back card(B)
					 subbnameRTC1GEKC(307),          -- GE back card(C)
					 subbnameRTC1GEKD(308),          -- GE back card(D)
					 subbnameRTC1GEPT(309),          -- GE process card(copper)
					 subbnameRTC1SAPA(310),          -- 4SA process card
					 subbnameRTC1SAKA(311),          -- 4SA back card
					 subbnameRTC1POPA(312),          -- POS process card
					 subbnameRTC1POK(313),           -- POS back card
					 subbnameRTC2POPB(314),          -- POS++ process card
					 subbnameRTC1CPOP(315),          -- CPOS process card
					 subbnameRTC1CPOB(316),          -- CPOS process card that supports t1
					 subbnameRTC1PAK(317),           -- CPOS/POS++ /8236 ATM back card
					 subbnameRTC1ATPA(318),          -- 8230 ATM process card
					 subbnameRTC1ATK(319),           -- 8230 ATM back card
					 subbnameRTC1ATPB(320),          -- 8236 ATM process card
					 subbnameRTC1T8IP(321),          -- 8-port T1 ATM process card
					 subbnameRTC18TKA(322),          -- 8-port T1 ATM back card
					 subbnameRTC18TKB(323),          -- 8-port T1 ATM back card
					 subbnameRTC1E8IP(324),          -- 8-port E1 ATM process card
					 subbnameRTC18EKA(325),          -- 8-port E1 ATM back card
					 subbnameRTC18EKB(326),          -- 8-port E1 ATM back card
					 subbnameRTC1ATSP(327),          -- 1-port ATM T3 process card
					 subbnameRTC1CT3K(328),          -- 1-port ATM T3 back card
					 subbnameRTC1AESP(329),          -- 1-port ATM E3 process card
					 subbnameRTC1CE3K(330),          -- 1-port ATM E3 back card
					 subbnameRTC1ATDP(331),          -- 2-port ATM T3 process card
					 subbnameRTC1T3DK(332),          -- 2-port ATM T3 back card
					 subbnameRTC1AEDP(333),          -- 2-port ATM E3 process card
					 subbnameRTC1E3DK(334),          -- 2-port ATM E3 back card
					 subbnameRTC1ATHP(335),          -- 622M ATM  process card
					 subbnameRTC1PAHA(336),          -- 622M ATM back card
					 subbnameRTC1PAHB(337),          -- 622M ATM back card
					 subbnameRTC1PAHC(338),          -- 622M ATM back card
					 subbnameRTC1CEPA(339),          -- 4-port CE1/e1 process card
					 subbnameRTC14EPB(340),          -- 4-port CE1/e1 process card
					 subbnameRTC14CEP(341),          -- 4-port CE1/e1 process card
					 subbnameRTC1QEKA(342),          -- 4-port CE1/e1 back card
					 subbnameRTC14EKA(343),          -- 4-port CE1/e1 back card
					 subbnameRTC14EKB(344),          -- 4-port CE1/e1 back card
					 subbnameRTC18EPA(345),          -- 8-port CE1/e1 process card
					 subbnameRTC18EPB(346),          -- 8-port CE1/e1 process card
					 subbnameRTC18CEP(347),          -- 8-port CE1/e1 process card
					 subbnameRTC1E3PA(348),          -- E3 process card
					 subbnameRTC1E3DP(349),          -- 2E3 process card
					 subbnameRTC1CE3P(350),          -- CE3 process card
					 subbnameRTC18TPA(351),          -- 8T1 process card
					 subbnameRTC18TPB(352),          -- 8T1 process card
					 subbnameRTC18CTP(353),          -- 8T1 process card
					 subbnameRTC1T3PA(354),          -- T3 process card
					 subbnameRTC1T3DP(355),          -- 2T3 process card
					 subbnameRTC1CT3P(356),          -- CT3 process card
					 subbnameRTC1CFPA(357),          -- flash card front
					 subbnameRTC1FEPA(358),          -- FETH card front
					 subbnameIMUETHP(359),           -- imu-eth card front
					 subbnameIMUETHK(360),           -- imu-eth card back
					 subbnameIMUGEOP(361),           -- imu-geo card front
					 subbnameIMUGEOK(362),           -- imu-geo card back
					 subbnameIMUGEEP(363),           -- imu-gee card front
					 subbnameIMUGEEK(364),           -- imu-gee card back
					 subbnameRTC14CTP(365),          -- NE05/08/16E:4t1 front
					 subbnameRTC14TKA(366),          -- NE05/08/16E:4t1 back
					 subbnameRTC1CPOC(367),          -- NE05/08/16E:CPOC front
-- 8011
					 subbnameCR01P4CM(400),          -- For NE80 & NE40, daughter card with 4 155M POS multimode optical port at 1300nm wavelength
					 subbnameCR01P4CS(401),          -- For NE80 & NE40, daughter card with 4 155M POS singlemode optical port at 1300nm wavelength (10-15km)
					 subbnameCR01P1HM(402),          -- For NE80 & NE40, daughter card with 1 622M POS multimode optical port at 1300nm wavelength
					 subbnameCR01P1HS(403),          -- For NE80 & NE40, daughter card with 1 622M POS singlemode optical port at 1300nm wavelength (10-15km)
					 subbnameCR01P1UZ(404),          -- For NE80 & NE40, daughter card with 1 2.5G POS singlemode optical port at 1300nm wavelenght (2km)
					 subbnameCR01P1US(405),          -- For NE80 & NE40, daughter card with 1 2.5G POS singlemode optical port at 1300nm wavelength (10-15km)
					 subbnameCR01P1UL(406),          -- For NE80 & NE40, daughter card with 1 2.5G POS singlemode optical port at 1300nm wavelength (40km)
					 subbnameCR01P1UV(407),          -- For NE80 & NE40, daughter card with 1 2.5G POS singlemode optical port at 1300nm wavelength (70km)
					 subbnameCR01P1RZ(408),          -- For NE80 & NE40, daughter card with 1 2.5G channelized POS singlemode optical port at 1300nm wavelength (2km)
					 subbnameCR01P1RS(409),          -- For NE80 & NE40, daughter card with 1 2.5G channelized POS singlemode optical port at 1300nm wavelength (10-15km)
					 subbnameCR01P1RL(410),          -- For NE80 & NE40, daughter card with 1 2.5G channelized POS singlemode optical port at 1300nm wavelength (40km)
					 subbnameCR01P1RV(411),          -- For NE80 & NE40, daughter card with 1 2.5G channelized POS singlemode optical port at 1300nm wavelength (70km)
					 subbnameCR01P4HM(412),          -- For NE80 & NE40, daughter card with 4 622M POS multimode optical port at 1300nm wavelength
					 subbnameCR01P4HS(413),          -- For NE80 & NE40, daughter card with 4 622M POS singlemode optical port at 1300nm wavelength (10-15km)
					 subbnameCR01A8CM(414),          -- For NE80 & NE40, daughter card with 8 155M ATM multimode optical port at 1300nm wavelength
					 subbnameCR01A8CS(415),          -- For NE80 & NE40, daughter card with 8 155M ATM singlemode optical port at 1300nm wavelength (10-15km)
					 subbnameCR01R1UZ(416),          -- For NE80 & NE40, daughter card with 1 2.5G RPR singlemode optical port at 1300nm wavelength (2km)
					 subbnameCR01R1US(417),          -- For NE80 & NE40, daughter card with 1 2.5G RPR singlemode optical port at 1300nm wavelength (10-15km)
					 subbnameCR01R1UL(418),          -- For NE80 & NE40, daughter card with 1 2.5G RPR singlemode optical port at 1300nm wavelength (40km)
					 subbnameCR01R1UV(419),          -- For NE80 & NE40, daughter card with 1 2.5G RPR singlemode optical port at 1300nm wavelength (70km)
					 subbnameCR01C2CF(420),          -- For NE80 & NE40, daughter card with 2 155M CPOS optical port (include SFP module)
					 subbnameCR01C4CF(421),          -- For NE80 & NE40, daughter card with 4 155M CPOS optical port (include SFP module)
					 subbnameCR01EGFE(422),          -- For NE80 & NE40, daughter card with 16 FE port
					 subbnameCR01EGFM(423),          -- For NE80 & NE40, daughter card with 16 FE multimode optical port at 1300nm wavelength
					 subbnameCR01EGFS(424),          -- For NE80 & NE40, daughter card with 16 FE singlemode optical port at 1300nm wavelength (10-15km)
					 subbnameCR01E2GP(425),          -- For NE80 & NE40, daughter card with 2 GE multimode optical port at 850nm wavelength
					 subbnameCR01E2GS(426),          -- For NE80 & NE40, daughter card with 2 GE singlemode optiacl port at 1300nm (10-15km)
					 subbnameCR01E2GQ(427),          -- For NE80 & NE40, daughter card with 2 GE singlemode optical port at 1550nm (40km)
					 subbnameCR01E2GV(428),          -- For NE80 & NE40, daughter card with 2 GE singlemode optical port at 1300nm (70km)
					 subbnameCR01E4GC(429),          -- For NE80 & NE40, daughter card with 4 GE optical port (include GIBC module)
					 subbnameCR01E8FB(430),          -- For NE80 & NE40, daughter card with 8 FE electronic/optical port
					 subbnameUR01A1CFF(431),
					 subbnameUR01A2CFF(432),
					 subbnameUR01A4CFF(433),
					 subbnameUR01A8CFF(434),
					 subbnameCR01A8CFF(435),
					 subbnameCR01A4CFF(436),
					 subbnameCR01SPUA(437),
					 subbnameCR01SPUB(438),
					 subbnameCR01SPUC(439),
					 subbnameCR018CT1(440),
					 subbnameCR01C1CF(441),
			-- New subboards for the SCUA board
					subbnameH511L24GA(450),      -- LAN switch subboard that provides two 5695s and 24 GE channels
					subbnameH511L12GA(451),      -- LAN switch subboard that provides one 5695 and 12 GE channels
					subbnameH511L02GA(452),      -- SERDES PHY subboard that provides two GE ports
					subbnameH511L02FA(453),      -- PHY subboard that provides two FE optical ports
					subbnameH511L02FE(454),          -- PHY subboard that provides two FE electric ports
					subbnameH511O4GS(455),       -- Subboard that provides four GE SFP optical ports
					subbnameH511O2GS(456),       -- Subboard that provides two GE SFP optical ports
					subbnameH511E2FA(457),       -- Subboard that provides two FE electric ports
					subbnameH511O2FS(458),       -- Subboard that provides two FE SFP optical ports

		  --New subboards for the IPMB board
					subbnameH601O2GNE(459),      -- Subboard that provides two GE optical ports (1310 nm, single-mode, 10 km, and LC interface)
					subbnameH601O2GNA(460),      -- Subboard that provides two GE optical ports (850 nm, multi-mode, 500 m, and LC interface)
					subbnameH601O2GNG(461),           -- Subboard that provides two GE optical ports (1510 nm, single-mode, 40 km, and LC interface

-- New subboards for the VPU board
					subbnamevpuh511O1FNG(462),      -- Subboard that provides one 100M Ethernet optical port (single-mode, 40 km)
					subbnamevpuh511O2FNG(463),      -- Subboard that provides two 100M Ethernet optical ports (single-mode, 40 km)
					subbnamevpuh511O2FNI(464),      -- Subboard that provides two 100M Ethernet optical ports (single-mode, 80 km)
					subbnamevpuh511O1GNI(465),      -- Subboard that provides one 1000M Ethernet optical port (single-mode, 80 km)
					subbnamevpuh511O1GNT(466),      -- Subboard that provides one 1000M Ethernet optical port (single-mode, 40 km)
-- A8010
					 subbnameCkmb(65536),            -- CKMB: clock subboard
					 subbnameP2ci(65537),            -- P2CI :subboard that provides two POS optical ports
					 subbnameCsma(65538),            -- CSMA: CSM/six-chip DSP subboard
					 subbnameCsmb(65539),            -- CSMB: CSM/12-M80310 chip DSP subboard
					 subbnameCsmc(65540),            -- CSMC: Mapletree-chip DSP subboard
					 subbnameCsmd(65541),            -- CSMD: CSM/12-M80320chip DSP subboard
					 subbnameCkma(65542),            -- CKMA0: SDH&TDM clock subboard
					 subbnameCkmc(65543),            -- CKMC0: TDM clock module (r002)
					 subbnameO8fib(65544),           -- 08FIB: subboard that provides eight 100M Ethernet optical ports (multi-mode, 2 km)
					 subbnameO8fif(65545),           -- 08FIF: subboard that provides eight 100M Ethernet optical ports (single-mode, 15 km)
					 subbnameO1gie(65546),           -- 01GIE: subboard that provides one GE optical port (single-mode, 10 km)
					 subbnameO1gig(65547),           -- 01GIG: subboard that provides one GE optical port (single-mode, 40 km)
					 subbnameO1gii(65548),           -- 01GII: subboard that provides one GE optical port (single-mode, 70 km)
					 subbnameO1gia(65549),           -- 01GIA: subboard that provides one GE optical port (multi-mode, 500 m)
					 subbnameOgfib(65550),           -- 0GFIB: subboard that provides 16 100M Ethernet optical ports (multi-mode, 2 km)
					 subbnameOgfif(65551),           -- 0GFIF: subboard that provides 16 100M Ethernet optical ports (single-mode, 15 km)
					 subbnameO2gie(65552),           -- 02GIE: subboard that provides two GE optical ports (single-mode, 10 km)
					 subbnameO2gia(65553),           -- 02GIA: subboard that provides two GE optical ports (multi-mode, 500 m)
					 subbnameP2cig(65554),           -- P2CIG: subboard that provides two 155M POS optical ports (single-mode, 30 km)
					 subbnameP2cib(65555),           -- P2CIB: subboard that provides two 155M POS optical ports (multi-mode, 2 km)
					 subbname8efi(65556),            -- E8FI: subboard that provides 8 10M/100M Ethernet electric ports
					 subbnameO2cib(65557),           -- 02CIB: subboard that provides two 155M ATM optical ports (multi-mode, 2 km)
					 subbnameO2cig(65558),           -- 02CIG: subboard that provides two 155M ATM optical ports (single-mode, 30 km)
					 subbnameE2ai(65559),            -- E2AI: subboard that provides two E3/T3 ATM electric ports   FRB
					 subbnameE8vd(65560),            -- E8VD: subboard that provides eight V.35 ports
					 subbnameE81d(65561),            -- E81d: subboard that provides eight E1/T1 twisted pairs
					 subbnameLdcu(65562),            -- LDCU: LZS data compression unit subboard
					 subbnameLiua(65563),            -- LIUA: subboard for the 16-channel E1 line (75 ohms) interface unit
					 subbnameLiub(65564),            -- LIUB: subboard for the 16-channel E1 line (120 ohms) interface unit (r002)
					 subbnameLiuc(65565),            -- LIUC: subboard for the 16-channel T1 line (100 ohms) interface unit (r002)
					 subbnameSelf(65566),            -- Virtual subboard of the board


					 subbnameCsme(65568),            -- CSME: CSM/6-chip DSP subboard
					 subbnameCsmg(65569),            -- CSMG: 60-channel/12 signal processing subboard (M80310)
					 subbnameCsmh(65570),            -- CSMH: 60-channel voice signal processing subboard (M80320)
-- MA5100
					 subbnameApc(65836),             -- APC subboard for the IMA board of the MA5105
					 subbnameH511O2GS2(65837),
					 subbnameH511O4GS2(65838),
					 subbnameH511E2FA2(65839),
					 subbnameH511O2FS2(65840),
-- MA5300
					 subbnameMa530016VPSL(65900),    -- 16-channel VDSL voice SPL board of the MA5300. Its BOM is 03024865.
					 subbnameMa530024VPSL(65901),    -- 24-channel VDSL voice SPL board of the MA5300
					 subbnameMa5300APSL(65902),      -- 48-channel ADSL voice SPL board of the MA5300
					 subbnameMa5300FE(65903),        -- 8-port FE board of the MA5300. This board provides four FE multi-mode optical ports and four
																-- FE electric ports. Its BOM is 03025505.
					 subbnameH531CQTA(65904),        -- Broadband line test subboard of the MA5100 and the MA5300. Its BOM is 03036794.
					 subbnameH531O2FAB(65905),       -- Subboard that provides four 10M/100M Ethernet optical ports (multi-mode, 2 km, and LC interface)
					 subbnameH53104FAF(65906),       -- Subboard that provides four 10M/100M Ethernet optical ports (single-mode, 15 km, and LC interface)
					 subbnameH531O2FAB2(65907),       -- Subboard that provides two 10M/100M Ethernet optical ports (multi-mode, 2 km, and LC interface)
					 subbnameH53104FAF2(65908),       -- Subboard that provides two 10M/100M Ethernet optical ports (single-mode, 15 km, and LC interface)
					 subbnameH531O2GAX(65909),       -- Subboard that provides two single-mode and multi-mode GE optical ports. Upstream GE port:
																-- single-mode, LC interface, and 10 km. Downstream GE port: multi-mode, LC interface, and 500 m.
					 subbnameH531R2HAF(65910),       -- Subboard that provides two 622M RPR optical ports (two 622M ports use one GE port)
																-- (single-mode, 15 km, and LC interface)
					 subbnameH531R2HAX(65911),       -- Subboard that provides two 622M single-mode RPR optical ports (two 622M ports use one GE port)
																-- (15 km, LC interface + one single-mode GE port, LC interface, and 10 km)
					 subbnameH531O1FAB(65912),       -- Subboard that provides one FE optical port (multi-mode, LC interface, and 2 km)
					 subbnameH531O1FAF(65913),       -- Subboard that provides one FE optical port (single-mode, LC interface, 15 km)
					 subbnameH531O1FAG(65914),       -- Subboard that provides one FE optical port (single-mode, LC interface, 40 km)
					 subbname5300H531E2GA(65915),        -- Subboard that provides two GE electric ports
					 subbnameTD91FEGA(65916),        -- Subboard that provides two GE electric ports and four FE electric ports
-- S3026V
					 subbnameLS66GS1UA(65920),       -- 1000M single-mode optical port board (10 km)
					 subbnameLS66GM1UA(65921),       -- 1000M multi-mode optical port board (500 m)
					 subbnameLS66FS1UA(65922),       -- 100M single-mode optical port board (15 km)
					 subbnameLS66FL1U(65923) ,       -- 100M single-mode optical port board (40 km)
					 subbnameLS66FM1UA(65924),       -- 100M multi-mode optical port board (2 km)
					 subbnameLS66GT1UA(65925),       -- 1000M electric port board
					 subbnameLS66ST1U(65926),        -- 1000M overlaid board
					 subbnameLS66GZ1UA(65927),       -- 1000M long-distance optical port board (70 km)
					 subbnameLS61GL1UA(65928),       -- 1000M medium-distance optical port board (40 km)

-- MA5100
					 subbnameH531E2GA(131082),           -- GE electric port board

					 subbnameH561M2GA(131083),           --MPLS subboard
					 subbnameH561L24GA(131084),          -- LSW subboard of the MA5600. It supports two 5695s and is similar to H511L24GA.
					 subbnameH561O4FM(131085),           -- MA5600's subboard that provides four FE optical ports
					 subbnameH561O2FM(131086),           -- MA5600's subboard that provides two FE optical ports
					 subbnameH561E4GFA(131087),          -- MA5600's subboard that provides four GE electric ports

					 --New subboards of the MA5100V3, which house control board ECUA
					 subbnameH511LSWA(131090),       -- LAN switch subboard (one 5650), which provides four GE ports and eight FE ports
					 subbnameH511LO2GB(131091),      -- PHY subboards
					 subbnameH511O3GS(131092),       -- Subboard that provides three GE SFP optical ports
					 subbnameH531E4FA(131093),       -- Subboard that provides four FE electric ports
					 subbnameH531O4FS(131094),       -- Subboard that provides four FE SFP optical ports

-- MA5200 add definition of sub card type  0x21000(135168) ~ 0x21FFF(139263)
					 subbnameH521P4CDM(135168),
					 subbnameH521P4CDS(135169),
					 subbnameH521P1HDM(135170),
					 subbnameH521P1HDS(135171),
					 subbnameH521P1UDZ(135172),
					 subbnameH521P1UDS(135173),
					 subbnameH521P1UDL(135174),
					 subbnameH521P1UDV(135175),
					 subbnameH521P1RDZ(135176),
					 subbnameH521P1RDS(135177),
					 subbnameH521P1RDL(135178),
					 subbnameH521P1RDV(135179),
					 subbnameH521P4HDM(135180),
					 subbnameH521P4HDS(135181),
					 subbnameCR01C4CF2(135182),
					 subbnameCR01C2CF2(135183),
					 subbnameH521E16FD(135184),
					 subbnameH521O16FDM(135185),
					 subbnameH521O16FDS(135186),
					 subbnameH521O2GDP(135187),
					 subbnameH521O2GDS(135188),
					 subbnameH521O2GDQ(135189),
					 subbnameH521O2GDV(135190),
					 subbnameH521O4GDG(135191),
					 subbnameH521O2GD(135192),
					 subbnameH521O8FDB(135193),
					 subbnameH521E4FD(135194),
					 subbnameH5218E1(135195),
					 subbnameH521E8FD(135196),
					 subbnameH521O8FDM(135197),
					 subbnameH521O8FDS(135198),
					 subbnameH521O1GDG(135199),
					 subbnameH521O2GDG(135200),
					 subbnameH521A4CDM(135201),
					 subbnameH521A4CDS(135202),
					 subbnameH521A8CDM(135203),
					 subbnameH521A8CDS(135204),
					 subbnameH521A2HDF(135205),
					 subbnameH521E8F(135206),
					 subbnameH521EGFE(135207),
					 subbnameH521E2GF(135208),
					 subbnameH521A8CFF(135209),
					 subbnameH521A2HFF(135210),
					 subbnameH521E3(135211),
					 subbnameH521T3(135212),
					 subbnameH521E1(135213),
					 subbnameH521T1(135214),
					 subbnameH522GXCE1T(135215),
					 subbnameH522GXCT1T(135216),
					 subbnameH5218CE1(135217),
					 subbnameH5218CT1(135218),
					 subbnameH522P2CFT(135219),
					 subbnameH522P4CFT(135220),
					 subbnameH522GERPR(135221),
					 subbnameH523POS10G(135222),
					 subbnameH523GE10GLAN(135223),
					 subbnameH523GE10GWAN(135224),
-- MA5600
					 subbnameH801O2GS(143360),          -- Subboard that provides two upstream GE optical ports. It is used for the SCUA upstream service.
					 subbnameH801O4GS(143361),          -- Subboard that provides four upstream GE optical ports. It is used for the SCUA upstream service.
					 subbnameH801O4FS(143362),          -- Subboard that provides four upstream FE optical ports. It is used for the SCUA upstream service.
					 subbnameH801E2GA(143363),          -- Subboard that provides two upstream GE electric ports. It is used for the SCUA upstream service.
					 subbnameH801O2CS(143364),          -- Swappable subboard that provides two ATM 155M optical ports
					 subbnameH801E4GA(143365),          -- Subboard for the H801SCUA board. It provides four electric ports.
					 subbnameH801D4GA(143366),          -- H801D4GA: subboard for the control board

					 subbnameH801O2FN(143367),          -- Subboard for the H801MCUA board. It provides two FE optical ports and provides the FE upstream service.
					 subbnameH801O2GN(143368),          -- Subboard for the H801MCUA board. It provides two GE optical ports and provides the GE upstream service.

					 subbnameH801EP1A(143371),          -- EPON upstream subboard, which is used for the MCUA upstream service
					 subbnameH801GP1A(143372),          -- GPON upstream subboard, which is used for the MCUA upstream service

					 subbnameH561EP1A(145920),          -- Subboard that provides one EPON port
					 subbnameH561EP2A(145921),          -- Subboard that provides two EPON ports
					 subbnameH561EP4A(145922),           -- Subboard that provides four EPON ports

					 subbnameH531O4GS(145923),          -- MA5600's subboard that provides four GE optical ports
					 subbnameH561BITS(145924),          -- BITS subboard for the H561AIUG board
					 subbnameH822EP1A(145925),          -- Subboard for the H821MCUA board. It provides one EPON port and two GE electric ports.
--ofa5920
					 subbnameH801TDMB(145933),          -- OFA5920 TDMoGEM subboard that supports two GPON boards and provides 8 E1 ports
					 subbnameH801EH1A(145934),          -- Subboard that provides 16-channel E1/T1 for the TDMoP board
					 subbnameH801CKMA(145935),          -- Clock subboard
					 subbnameH802CKMA(146037),          -- MA5600T clock subboard:H802CKMA
					 subbnameH801FLBA(145938),          -- Voice forwarding logic subboard
					 subbnameH801NH1A(145940),          -- TDM subboard for the H801TOPA board
					 subbnameH801CSSA(146017),          -- 2-channel STM-1 uplink subboard
					 subbnameH801O2CE(146021),          -- 2-channel STM-1 uplink subboard
					 subbnameH802GP1A(146022),          -- H801GP1A cost-reduce
					 subbnameH801X1HA(146023),          -- Subboard for the H801ETHB board.
					 subbnameH801CKMC(146024),          -- Clock subboard for the H801SCUL and H801SCUN board
					 subbnameH801M2XA(146025),          -- New subboard for SCUN
					 subbnameH801BITSB(146038),         -- Clock subboard for the H801CITD board
					 subbnameH801CPCA(204923),          -- Clock subboard for the H801MCUD board.
					 subbnameH801CPCB(204933),          -- Clock subboard for the H801MCUD1 board.
					 subbnameH801CPCC(204934),          -- Clock subboard for the H801MCUE board.
					 subbnameH801CKMD(888891),          -- Clock subboard.

--MA5800
					 subbnameH901CKUA(148501),          -- Clock subboard of MA5800 H901MPLB

-- WA5700:
					 subnameBWAE1(155648),             -- E1 subboard for the IDU control board of the BWA
					 subnameBWAT1(155649),             -- T1 subboard for the IDU control board of the BWA
					 subnameBWAGE(155650),             -- GE subboard for the IDU control board of the BWA
-- MA561X
					 subbnameH831EP1A(155651),          -- EPON upstream subboard, which is used for the 561X upstream service
					 subbnameH831GP1A(155652),          -- GPON upstream subboard, which is used for the 561X upstream service
					 subbnameH831GE1A(155653),          -- GE   upstream subboard, which is used for the 561X upstream service
					 subbnameH836ASDA(155654),          --VOIP DSP Subboard H836ASDA
					 subbnameH831PSUH(155655),          --Power Subboard

-- MA5612
					 subbnameH832EP2A(155656),          -- EPON upstream subboard, which is used for the 561X upstream service +-
					 subbnameH833GP2A(155657),          -- GPON upstream subboard, which is used for the 561X upstream service


					 subbnameH831UP2A(155658),          -- Auto adapt upstream subboard, which is used for the MDU upstream service
					 subbnameH831UP2C(155659),          -- Auto adapt upstream subboard with Clock, which is used for the MDU upstream service
					 subbnameH831GR1A(155660),          -- RF upstream subboard, which is used for the MDU upstream service
					 subbnameH831UP2D(155661),          -- Auto adapt upstream subboard, which is used for the MA5631(SD5103) upstream service
					 subbnameH836ASDM(155662),          --VOIP 128 Tunnel DSP Subboard H836ASDM
					 subbnameH832TP2C(155663),          --10G EPON subboard
					 subbnameH832TP2D(155664),          --10G EPON subboard
					 subbnameH831XP1A(155665),          --10G GPON subboard
-- MA5662
					 subbnameH821MODA(155666),          --56K MODEM subboard
					 subbnameH821PRCA(155667),          --RFT-C subboard

					 subbnameH832TP1C(155668),          --1*10G EPON subboard

-- MA5616
					 subbnameVPB(155934),          -- VECTOR Subboard VPB
					 subbnameVPD(155949),          -- VECTOR Subboard VPD

-- MA5616A
				 subbnameH833XP1A(155935),       -- 10 GPON Subboard
				  subbnameH833XP1C(155936),       -- 10 GPON Subboard

-- MA5616
		subbnameVPA(155950),           -- VECTOR Subboard VPA

-- MA5694S
					 subbnameH831VD4A(155951),       -- VD4A  Subboard for MA5694S

		subbnameH831UP2E(155952),       -- Auto adapt upstream subboard of MA5633, It supports EQAM
		subbnameH831UP2F(155953),       -- Auto adapt upstream subboard of MA5633, It not supports EQAM
		subbnameHS21PWBB(155954),       -- Virtual power subboard of MA5633
		subbnameHS21MIXB(155955),       -- Virtual mixer subboard of MA5633

-- WLAN
					 subbnameWA611POEA(160000),         --Power Subboard of WA611WACA

-- MD
					 subbnamebs22o1hdi(200704),         -- ATM subboard that provides one long-distance 622M optical port (single-mode, SD537 chip, 70 km)

-- UA
					 subbnameH601O1GNI(204805),       --H601O1GNI: subboard that provides one 1000M Ethernet optical port (single-mode, 80 km)
					 subbnameH601O2GNI(204806),       --H601O2GNI: subboard that provides two 1000M Ethernet optical ports (single-mode, 80 km)
					 subbnameH601O2FNG(204807),       --H601O2FNG: subboard that provides two 100M Ethernet optical ports (single-mode, 40 km)
					 subbnameH601O1GNT(204808),       --H601O1GNT: subboard that provides one 1000M Ethernet optical port (single-mode, 40 km, and 1310 nm).
																 -- The IPM control board supports this subboard.
					 subbnameH601O1FNG(204809),       --H601O1FNG: subboard that provides one 100M Ethernet optical port (single-mode, 40 km)
					 subbnameH601O1FNI(204810),       --H601O1FNI: subboard that provides one 100M Ethernet optical port (single-mode, 80 km)

-- AG
					 subbnameBCM1510(204811),         --Subboard BCM1510, which uses the DSP chip and is attached to the PVM control board
					 subbnameVPC1510(204812),         --Subboard VPC1510, which is a voice subboard and is attached to the PVM control board
					 subbnameH602ETCA(204813),        --Subboard H602ETCA, which is a voice subboard and is attached to the PVM control board
					 subbnameH601ETCA(204814),        --Subboard H601ETCA, which is a voice subboard and is attached to the PVM control board
					 subbnameH801ETCA(204815),        --VoIP subboard with the TI chipset
					 subbnameH802ETCA(204816),        --VoIP subboard with the MIRO chipset
					 subbnameH602ETCB(204818),        --Subboard H602ETCB, which is a double-chip MIRO voice subboard and is attached to the PVM control board
					 subbnameH602ETCC(204819),        --Subboard H602ETCC, which is a triple-chip MIRO voice subboard and is attached to the PVM control board


-- UA
					 subbnameH601E13F(204820),        --Subboard for the APM or AIU board. It provides one front-access E3 port.
					 subbnameH601E23F(204821),        --Subboard for the APM or AIU board. It provides two front-access E3 ports.
					 subbnameH601T13F(204822),        --Subboard for the APM or AIU board. It provides one front-access T3 port.
					 subbnameH601T23F(204823),        --Subboard for the APM or AIU board. It provides two front-access T3 ports.

					 subbnameH601M2GS(204830),        -- MPLS subboard for the IPMP board. It provides four optical ports.


					 subbnameH601ETCB(204831),        --Subboard H601ETCB, which is a double-chip TI voice subboard and is attached to the PVM control board
					 subbnameH601ETCC(204832),        --Subboard H601ETCC, which is a triple-chip TI voice subboard and is attached to the PVM control board

					 subbnameH601O2GNI2(204833),       --Subboard that provides two GE optical ports (1550 nm, single-mode, 80 km, and LC interface)
					 subbnameH601O2GNT(204834),       --Subboard that provides two GE optical ports (1310 nm, single-mode, 40 km, and LC interface)
					 subbnameH602O1GNT(204835),       --Subboard that provides one GE optical port (1310 nm, single-mode, 40 km, and LC interface)
					 subbnameH602O1GNI(204836),       --Subboard that provides one 1000M Ethernet optical port (single-mode, 80 km)
					 subbnameH601O2FNG2(204837),   --Subboard that provides two 100M Ethernet optical ports (single-mode, 40 km)
					 subbnameH601O1FNG2(204838),       --Subboard that provides one 100M Ethernet optical port (single-mode, 40 km)
					 subbnameH601O1FNI2(204839),   --Subboard that provides one 100M Ethernet optical port (single-mode, 80 km)
					 subbnameH612O2FN(204840),         --Subboard that provides two FE optical ports
					 subbnameH61202GN(204841),         --Subboard that provides two GE optical ports

				--tangrong changed for conflictted with  subbnameH612O2FN(204840)
					 subbnameH602V1HAI(204842),         -- H602V1HAI: VPRING subboard that provides one 622M optical port (single-mode, 70 km, SC interface, and SD537)

					 subbnameH602ETCM( 262144 ),        --Subboard H602ETCM, which is a single-chip MINI voice subboard and is attached to the PVM control board
					 subbnameH602ETCN( 262145),         --Subboard H602ETCN, which is a double-chip MINI voice subboard and is attached to the PVM control board
					 subbnameH601EO1A(262146),          -- EPON upstream subboard, which is used for the UA5000 upstream service
					 subbnameH601GO1A(262147),          -- GPON upstream subboard, which is used for the UA5000 upstream service
					 subbnameH601GE2A(262148),          -- GE   upstream subboard, which is used for the UA5000 upstream service
-- NE40&80
					 subbname8CE1(528640),         --8 Ports,RJ45,Channelized E1,Flexible Card
					 subbnameGCE1(528641),         -- 16-port Channelized E1,RJ45 Interface Line Card
					 subbnameE4GS(528642),         -- 4-Port Gigabit Ethernet Optical Interface Line Process Card (MTRJ,Single-mode,10km)
					 subbnameE4GP(528643),         -- 4-Port Gigabit Ethernet Optical Interface Line Process Card(MTRJ,Multi-mode,500m)
					 subbnameE4GQ(528644),         -- 4-Port Gigabit Ethernet Optical Interface Line Process Card(LC,Single-mode,1550nm,40km)
					 subbnameE4GV(528645),         -- 4-Port Gigabit Ethernet Optical Interface Line Process Card (LC,Single-mode,1550nm,70km)
					 subbnameP2HM(528646),         -- 2-Port OC-12c/STM-4c POS Optical Interface Line Process Card(SC,Multi-mode,1300nm,500m)
					 subbnameP2HS(528647),         -- 2-Port OC-12c/STM-4c POS Optical Interface Line Process Card(SC,Single-mode,1300nm,15km)
					 subbnameP8CM(528648),         -- 8-Port OC-3c/STM-1 POS Optical Interface Line Process Card(MTRJ,Multi-mode,2km)
					 subbnameP8CS(528649),         -- 8-Port OC-3c/STM-1 POS Optical Interface Line Process Card(MTRJ,Single-mode,15km)
					 subbnameE4FE(528650),         --
					 subbnameEGFE(528651),         -- 16-Port Fast Ethernet Electrical Interface Line Process Card(RJ45)
					 subbnameEGFS(528652),         -- 16-Port Fast Ethernet Optical Interface Line Process Card(MTRJ,Single-mode,15km)
					 subbnameEGFM(528653),         -- 16-Port Fast Ethernet Optical Interface Line Process Card(MTRJ,Multi-mode,1300nm,2km)
					 subbnameE4GC(528654),         -- 4 Ports Gigabits Ethernet GBIC Interface Line Card_LAN
					 subbnameEGFEM(528655),      -- Subboard that provides 16 FE RJ45 electric ports
					 subbnameLGFSM(528656),      -- Subboard that provides 16 FE MTRJ optical ports (single-mode, 1300 nm, and 15 km)
					 subbnameEGFMM(528657),      -- Subboard that provides 16 FE MTRJ optical ports (multi-mode, 1300 nm, and 2 km)
					 subbnameE4GSM(528658),      -- Subboard that provides four GE MTRJ optical ports (single-mode, 1300 nm, and 10 km)
					 subbnameE4GPM(528659),      -- Subboard that provides four GE MTRJ optical ports (multi-mode, 850 nm, and 500 m)
					 subbnameE4GQM(528660),      -- Subboard that provides four GE optical ports (single-mode, 1550 nm, and 40 km, LC interface)
					 subbnameE4GVM(528661),      -- LAN subboard that provides four GE optical ports (single-mode, 1550 nm, 70 km, and LC interface)
					 subbnameE4GCM(528662),      -- Subboard that provides four GE ports and supports four hot swappable GBIC optical modules.
																-- Currently, the following optical modules are available: 850nm 500m, 1310nm 10km/30km, and 1550nm 70km.
					 subbnameE4GEM(528663),      -- Subboard that provides four optical/electro (O/E) auto-sensing ports,
																-- and supports the SFP optical port or the RJ45 electric port.
					 subbnameEWFEM(528664),      -- Subboard that provides 32 FE electric ports, and supports the MPLS service
					 subbnameEGFEF(528665),        -- 16FE_RJ45 Flexible Card
					 subbnameP1CFF(528666),        -- 1POS155_SFP Flexible Plug Card
					 subbnameP2CFF(528667),        -- 2POS155_SFP Flexible Plug Card
					 subbnameP4CFF(528668),        -- 4 Port POS155 SFP Optical Interface Line Process Card
					 subbnameE8FF(528669),         -- 8*FE Optical Interface Line Card-SFP
					 subbnameE1GFF(528670),        -- 1GE_SFP Flexible Plug Card
					 subbnameE2GFF(528671),        -- 2GE_SFP Flexible Plug Card
					 subbnameA2HFF(528672),        -- 2-Port OC-12C/STM-4C ATM Optical LC-SFP
					 subbname3E3(528673),          -- 3 Ports,SMB,E3,Flexible Card
					 subbname3T3(528674),          -- 3 Ports,SMB,T3,Flexible Card
					 subbnameE0GFF(528675),        -- NAT Flexible Plug Card
					 subbnameETGFF(528676),        -- NATPT Flexible Plug Card
					 subbnameSNGFF(528677),        -- NetStream Flexible Plug Card
					 subbnameSTGFF(528678),        -- L2TP Flexible Plug Card
					 subbnameSGGFF(528679),        -- GRE Flexible Plug Card
					 subbname8E1(528680),          -- 8 Ports E1 Interface Line Card_RJ45
					 subbnameA2HF(528681),         --
					 subbnameEGFEE(528682),        -- 16 Ports FE RJ45 Electrical Interface Line Card_LAN
					 subbnameEWFE(528683),         --
					 subbnameE4GE(528684),         --
					 subbnameEGFSM(528685),        -- 16*FE 1300nm15km-MTRJ
					 subbnameR1UF(528686),         -- 1*OC-48c/STM-16c RPR-SFP Optical Interface Line Card
					 subbnameN2GB(528687),         -- Netstream
					 subbnameP4CM(528688),         -- For NE80 & NE40, daughter card with 4 155M POS multimode optical port at 1300nm wavelength
					 subbnameP4CS(528689),         -- For NE80 & NE40, daughter card with 4 155M POS singlemode optical port at 1300nm wavelength (10-15km)
					 subbnameP1HM(528690),         -- For NE80 & NE40, daughter card with 1 622M POS multimode optical port at 1300nm wavelength
					 subbnameP1HS(528691),         -- For NE80 & NE40, daughter card with 1 622M POS singlemode optical port at 1300nm wavelength (10-15km)
					 subbnameP1UZ(528692),         -- For NE80 & NE40, daughter card with 1 2.5G POS singlemode optical port at 1300nm wavelenght (2km)
					 subbnameP1US(528693),         -- For NE80 & NE40, daughter card with 1 2.5G POS singlemode optical port at 1300nm wavelength (10-15km)
					 subbnameP1UL(528694),         -- For NE80 & NE40, daughter card with 1 2.5G POS singlemode optical port at 1300nm wavelength (40km)
					 subbnameP1UV(528695),         -- For NE80 & NE40, daughter card with 1 2.5G POS singlemode optical port at 1300nm wavelength (70km)
					 subbnameP1RZ(528696),         -- For NE80 & NE40, daughter card with 1 2.5G channelized POS singlemode optical port at 1300nm wavelength (2km)
					 subbnameP1RS(528697),         -- For NE80 & NE40, daughter card with 1 2.5G channelized POS singlemode optical port at 1300nm wavelength (10-15km)
					 subbnameP1RL(528698),         -- For NE80 & NE40, daughter card with 1 2.5G channelized POS singlemode optical port at 1300nm wavelength (40km)
					 subbnameP1RV(528699),         -- For NE80 & NE40, daughter card with 1 2.5G channelized POS singlemode optical port at 1300nm wavelength (70km)
					 subbnameP4HM(528700),         -- For NE80 & NE40, daughter card with 4 622M POS multimode optical port at 1300nm wavelength
					 subbnameP4HS(528701),         -- For NE80 & NE40, daughter card with 4 622M POS singlemode optical port at 1300nm wavelength (10-15km)
					 subbnameA8CM(528702),         -- For NE80 & NE40, daughter card with 8 155M ATM multimode optical port at 1300nm wavelength
					 subbnameA8CS(528703),         -- For NE80 & NE40, daughter card with 8 155M ATM singlemode optical port at 1300nm wavelength (10-15km)
					 subbnameR1UZ(528704),         -- For NE80 & NE40, daughter card with 1 2.5G RPR singlemode optical port at 1300nm wavelength (2km)
					 subbnameR1US(528705),         -- For NE80 & NE40, daughter card with 1 2.5G RPR singlemode optical port at 1300nm wavelength (10-15km)
					 subbnameR1UL(528706),         -- For NE80 & NE40, daughter card with 1 2.5G RPR singlemode optical port at 1300nm wavelength (40km)
					 subbnameR1UV(528707),         -- For NE80 & NE40, daughter card with 1 2.5G RPR singlemode optical port at 1300nm wavelength (70km)
					 subbnameC2CF(528708),         -- For NE80 & NE40, daughter card with 2 155M CPOS optical port (include SFP module)
					 subbnameC4CF(528709),         -- For NE80 & NE40, daughter card with 4 155M CPOS optical port (include SFP module)
					 subbnameE2GP(528710),         -- For NE80 & NE40, daughter card with 2 GE multimode optical port at 850nm wavelength
					 subbnameE2GS(528711),         -- For NE80 & NE40, daughter card with 2 GE singlemode optiacl port at 1300nm (10-15km)
					 subbnameE2GQ(528712),         -- For NE80 & NE40, daughter card with 2 GE singlemode optical port at 1550nm (40km)
					 subbnameE2GV(528713),         -- For NE80 & NE40, daughter card with 2 GE singlemode optical port at 1300nm (70km)
					 subbnameE8FB(528714),         -- For NE80 & NE40, daughter card with 8 FE electronic/optical port
					 subbnameA1CFF(528715),        -- 1-port STS-3C/STM-1 ATM SFP Optical Interface Flexible Plug Card
					 subbnameA2CFF(528716),        -- 2-port STS-3C/STM-1 ATM SFP Optical Interface Flexible Plug Card
					 subbnameA4CFF(528717),        -- 4 Ports STS-3C/STM-1 ATM SFP Optical Interface Line Card
					 subbnameA8CFF(528718),        -- 8-port STS-3C/STM-1 ATM SFP Optical Interface Flexible Plug Card
					 subbname8CT1(528719),         --
					 subbnameC1CF(528720),         -- 1-Port Channelized OC-3/STM-1 to DS0 SFP Optical Interface Line Card
					 subbnameE8FEF(528721),        -- 8FE_RJ45 Flexible Card
					 subbnameP1HF(528722),         --
					 subbnameEWFEE(528723),        -- 32 Ports FE RJ45 Electrical Interface Line Card
					 subbnameEGFT(528724),         -- 16-Port Fast Ethernet Optical Interface Line Process Card(Single-mode,1550nm,15km,LC)
					 subbnameCR01OPMQ(528725),     -- Single-mode,1550nm,LC Interface Optical Protection Module
					 subbnameCR01OPMZ(528726),     -- Single-mode,1300nm,LC Interface Optical Protection Module
					 subbnameCR01OPMM(528727),     -- Multi-mode,1300nm,LC Interface Optical Protection Module
					 subbnameCR01OPMP(528728),     -- Multi-mode,850nm,LC Interface Optical Protection Module
					 subbnameSPCB(528729),         -- 4*FE-RJ45 And 4*FE-SFP And 4*OC-3c/STM-1 POS Multi-mode 1300nm 2km-MTRJ Interface Line Card
					 subbnameEGFSE(528730),        -- CR01EGFSE0
					 subbnameEGFME(528731),        -- CR01EGFME0
					 subbnameP8CFF(528732),        -- 8 Port POS155 SFP Optical Interface Line Process Card
					 subbnameE4GFF(528733),        -- 4-port GE SFP Interface Line Card
					 subbnameEGFF(528734),         -- 16*FE Optical Interface Line Card-SFP
					 subbnameP2HF(528735),         -- CR03P2HF-2*OC-12c/STM-4c-POS-SFP Optical Interface Card

-- 8031
					 subbnameCX61E1XX0(536577),      -- CX600-1-port 10G Ethernet LAN Optical Interface LPU (Enhanced)
					 subbnameCX61W1XX0(536578),      -- CX600 1-port 10G Ethernet WAN Optical Interface LPU (Enhanced)
					 subbnameCX61EAGF0(536579),      -- CX600-10-port Gigabit Ethernet Optical Interface LPU (Enhanced)
					 subbnameCX61EFGE0(536580),      -- CX600-24-port 10M/100M/1000M Ethernet Electrical Interface LPU(Enhanced)
					 subbnameCX61E2XXE0(536581),     -- CX600-2-port 10G Ethernet LAN Optical Interface LPU
					 subbnameCX61EFGEE0(536582),     -- CX600-24-port 10M/100M/1000M Ethernet Electrical Interface LPU
					 subbnameCX61EFGFE0(536583),     -- CX600-24-port Gigabit Ethernet Optical Interface LPU
					 subbnameCX61EMGEE0(536584),     -- CX600-48-port 10M/100M/1000M Ethernet Electrical Interface LPU
					 subbnameCX61EMGFE0(536585),     -- CX600-48-port Gigabit Ethernet Optical Interface LPU
					 subbnameCX61E1XS0(536586),      -- CX600-NetEngine-CR61E1XS0-1*10GE LAN 1310nm 10km-LC
					 subbnameCX61E1XQ0(536587),      -- CX600-NetEngine-CR61E1XQ0-1*10GE LAN 1550nm 40km-LC
					 subbnameCX61W1XS0(536588),      -- CX600-NetEngine-CR61W1XS0-1*10GE WAN 1310nm 10km-LC
					 subbnameCX61W1XQ0(536589),      -- CX600-NetEngine-CR61W1XQ0-1*10GE WAN 1550nm 40km-LC
					 subbnameCX61W1XV0(536590),      -- CX600-NetEngine-CR61W1XV0-1*10GE WAN 1550nm 80km-LC
					 subbnameCX61R1XX(536591),       ---CX600-CX61R1XX0-1*OC-192c/STM-64c RPR-XFP
					 subbnameCX61R4UF(536592),       ---CX600-CX61R4UF0-4*OC-48c/STM-16c RPR-SFP
					 subbnameCX61R2GF(536593),       -- CX600-CX61R2GF0-2*GE/STM-16c RPR-SFP
					 subbnameCX61R4GF(536594),       -- CX600-CX61R4GF0-4*GE/STM-16c RPR-SFP
					 subbnameCX61EFFF(536595),       -- CX600-CX61EFFF0-24
					 subbnameCX61R2UF(536596),       ---CX600-CX61R2UF0-2*OC-48c/STM-16c RPR-SFP
					 subbnameCX61E1XXA(536597),      ---CX600-CX61E1XXA-1 10GE-Lan/Wan
					 subbnameCX61EBGF(536598),       ---CX600-CR52EBGF0,12-port 100/1000Base-X SFP Flexible Interface Daughter Card
					 subbnameCX61EBGE(536599),       ---CX600-CR52EBGE0,12-port 10/100/1000Base-TX RJ45 Flexible Interface Daughter Card
					 subbnameCX61L1XX(536600),       ---CX600-CR52L1XX0,1-port 10GBase WAN/LAN XFP Flexible Interface Daughter Card
					 subbnameCx61L4XX(536601),       ---CX600-CR52L4XX0,4-port 10GBase WAN/LAN-XFP Flexible Card(Occupy two sub-slots)
					 subbnameCX61EKGE(536602),       ---CX600-CR52EKGE0,40-port 10/100/1000Base-RJ45 Flexible Card (Occupy two sub-slots)
					 subbnameCX61EKGF(536603),       ---CX600-CR52EKGF0,40-Port 100/1000Base-SFP Flexible Card(Occupy two sub-slots)
					 subbnameCX61P1XXB(536604),      ---CX600-CR52P1XXBZ0,1 port OC-192c/STM-64c POS-XFP Flexible Card
					 subbnameCX67E8GF(536605),       -- CX600-X1 Interface
					 subbnameCX67E8GFA(536606),      -- CX600-X1 Interface
					 subbnameCX67E8FF(536607),       -- CX600-X1 Interface
					 subbnameCX67E8FE(536608),       -- CX600-X1 Interface
					 subbnameCX67DE1(536609),        -- CX600-X1 Interface
					 subbnameCX67DE1A(536610),       -- CX600-X1 Interface
					 subbnameCX67C1CF(536611),       -- CX600-X1 Interface
					 subbnameCX67AUXQ(536612),       -- CX600-X1 Interface
					 subbnameCX67VNPUICARD(536613),  -- CX600-X1 Interface
					 subbnameCX22E2XX(536614),       -- CX22E2XX-4*10GE
					 subbnameCX22E4GF(536615),       -- CX22E4GF-4*GE
					 subbnameCX0235000d22E4GFA(536616), -- 0235000dCX22E4GFA-4*GE
					 subbnameCX22E2XEA(536617),      -- CX22E2XEA-2*10GE,RJ45
					 subbnameCX22E4XY(536618),       -- CX22E4XY-4*10GE,XFP
					 subbnameCX22E2XY(536619),       -- CX22E2XY-2*10GE,XFP
					 subbnameCXTPB(536620),          -- TPB
					 subbnameCX0235000bFAN(536621),  -- 0235000bFAN
					 subbnameCx0235000aPOWER(536622),-- 0235000aPOWER
					 subbnameCX0235000cTPC(536623),  -- 0235000cTPC
					 subbnameCX03020PWP22E4GFA(536624),-- 03020PWPCX22E4GFA-4*GE
					 subbnameCX03020NPWTPC(536625),  -- 03020NPWTPC
					 subbnameCX03020GFAFAN(536626),  -- 03020GFAFAN
					 subbnameCX03020LXPPOWER(536627),-- 03020LXPPOWER
					 subbnameCX03020LYXPOWER(536628),-- 03020LYXPOWER
					 subbnameCX02316783POWER(536629),-- 02316783POWER
					 subbnameCX02316784POWER(536630),-- 02316784POWER
					 subbnameCX02351651FAN(536631),  -- 02351651FAN
					 subbnameCX02130877POWER(536632),-- 02130877POWER,180w POE
					 subbnameCX02130878POWER(536633),-- 02130878POWER,250W POE
					 subbnameCX02130879POWER(536634),-- 02130879POWER,500W POE

					 subbnameCX62E8GF0(536635),                  -- CX600-X1-DO/CX600-X2-DO 8-Port 100/1000Base-X-SFP High-speed Interface Card (HIC)
					 subbnameCX62E8GFA0(536636),                 -- CX600-X1-DO/CX600-X2-DO 8-Port 100/1000Base-X-SFP High-speed Interface Card A (HIC, Supporting 1588v2)
					 subbnameCX62E8FF0(536637),                  -- CX600-X1-DO/CX600-X2-DO 8-Port 100Base-X-SFP Flexible Interface Card (FIC, Supporting 1588v2)
					 subbnameCX62E8FE0(536638),                  -- CX600-X1-DO/CX600-X2-DO 8-Port 100Base-RJ45 Flexible Interface Card (FIC, Supporting 1588v2)
					 subbnameCX62C1CF0(536639),                  -- CX600-X1-DO/CX600-X2-DO 1-Port Channelized OC-3c/STM-1c POS-SFP Flexible Interface Card (FIC)
					 subbnameCX62DE10(536640),                   -- CX600-X1-DO/CX600-X2-DO 16-Port E1(75ohm) Flexible Interface Card (FIC)
					 subbnameCX62DE1A0(536641),                  -- CX600-X1-DO/CX600-X2-DO 16-Port E1(120ohm) Flexible Interface Card (FIC)
					 subbnameCX62AUXQ0(536642),                  -- CX600-X1-DO/CX600-X2-DO Auxiliary Flexible Interface Card with 4-Port 100Base-RJ45(FIC, Supporting 1588v2)
					 subbnameCX62E8GF1(536643),                  -- CX600-DO 8-Port 100/1000Base-X-SFP Flexible Card(S10)
					 subbnameCX62E8GFB0(536644),                 -- CX600-DO 8-Port 100/1000Base-X-SFP Flexible Card A(S10-A,Supporting 1588v2)
					 subbnameCX62A2HF0(536645),                  -- CX600-DO 2-Port OC-12c/STM-4c ATM-SFP Flexible Card(S10)
					 subbnameCX62A4CF1(536646),                  -- CX600-DO 4-Port OC-3c/STM-1c ATM-SFP Flexible Card(S10)
					 subbnameCX62C2CF0(536647),                  -- CX600-DO 2-Port Channelized OC-3c/STM-1c POS-SFP Flexible Card(S10)
					 subbnameCX62CFE10(536648),                  -- CX600-DO 24-Port Channelized E1/T1-DB100 Flexible Card(S10)
					 subbnameCX62L1XX0(536649),                  -- CX600-DO 8-Port 1-Port 10GBase LAN/WAN-XFP Flexible Card(S20)
					 subbnameCX62EBGF0(536650),                  -- CX600-DO 12-Port 100/1000Base-X-SFP Flexible Card(S20)

					 subbnameCX62EBGE0(536651),                  -- CX600-DO 8-Port 12-Port 10/100/1000Base-RJ45 Flexible Card(S20)
					 subbnameCX62L1XXB0(536652),                 -- CX600-DO 8-Port 1-Port 10GBase LAN/WAN-XFP Flexible Card A(S20-A,Supporting 1588v2)
					 subbnameCX62EBGFB0(536653),                 -- CX600-DO 12-Port 100/1000Base-X-SFP Flexible Card A(S20-A,Supporting 1588v2)
					 subbnameCX62EKGF0(536654),                  -- CX600-DO 40-Port 100/1000Base-X-SFP Flexible Card(S20,Occupy two sub-slots)
					 subbnameCX62EKGE0(536655),                  -- CX600-DO 40-Port 10/100/1000Base-RJ45 Flexible Card(S20,Occupy two sub-slots)
					 subbnameCX62L4XX0(536656),                  -- CX600-DO 4-Port 10GBase LAN/WAN-XFP Flexible Card(S20,Occupy two sub-slots)
					 subbnameCX62L2XEEGF0(53657),                -- CX600-DO 2-Port 10GBase LAN/WAN-XFP+20-Port 100/1000Base-X-SFP Flexible Card(S20,Occupy two sub-slots)

					 subbnameCX62EMFE0(536658),                  -- CX600-DO 48-Port 10/100Base Delander Flexible Card(S20,Occupy one sub-slot)
					 subbnameCX62L2XXN0(536659),                 -- CX600-DO 2-Port 10GBase LAN/WAN-XFP Flexible Card(S40)
					 subbnameCX62EEGFN0(536660),                 -- CX600-DO 20-Port 100/1000Base-X-SFP Flexible Card(S40)
					 subbnameCX62L2XXNB0(536661),                -- CX600-DO 2-Port 10GBase LAN/WAN-XFP Flexible Card A(S40-A,Supporting 1588v2)
					 subbnameCX62EEGFNB0(536662),                -- CX600-DO 20-Port 100/1000Base-X-SFP Flexible Card A(S40-A,Supporting 1588v2)
					 subbnameES510X2X(536663),                    -- ES510X2X-2*10GE
					 subbnameES510G4S(536664),                    -- ES510G4S-4*GE
					 subbnameES510G4SA(536665),                   -- ES510G4SA-4*GE
					 subbnameES510X4S(536666),                    -- ES510X4S-4*10GE,XFP
					 subbnameES510X2S(536667),                    -- ES510X2S-2*10GE,XFP
					 subbnameTPC(536668),                         -- TPC

					 subbnameLS510X4SA(536669),                -- 4-Port GE SFP or 10GE SFP+ Optical Interface Card (Used In HI Series)
					 subbnameLS510X2SA(536670),                -- 2-Port GE SFP or GE SFP/10GE SFP+ Optical Interface Card (Used In HI Series)
					 subbnameLS510G4SC(536671),                -- 4-Port GE SFP Optical Interface Card (Used In HI Series)
					 subbnameLS310G2S(536672),                 -- 2-Port GE SFP Optical Interface Card (Used In HI Series)

					 subbname02130911POWER(536673),            -- 02130911POWER
					 subbname03020WFNPOWER(536674),            -- 03020WFNPOWER
					 subbname02353514FAN(536675),              -- 02353514FAN
					 subbnameCX61A4CFN(536721),                ---CX600-X1/X2,4-port STS-3C/STM-1 ATM SFP Optical Interface Flexible Plug Card
					 subbnameCX67E4GF(536722),                ---CX600-X1/X2,4-port GE SFP Optical Interface Flexible Plug Card

					 subbnameES510X4SA(536676),                -- ES510X4SA  4-Port GE SFP or 10GE SFP+ Optical Interface Card (Used In HI Series)
					 subbnameES510X2SA(536677),                -- ES510X2SA 2-Port GE SFP or GE SFP/10GE SFP+ Optical Interface Card (Used In HI Series)
					 subbnameES510G4SC(536678),                -- ES510G4SC 4-Port GE SFP Optical Interface Card (Used In HI Series)
					 subbnameES310G2S(536679),                 -- ES310G2S 2-Port GE SFP Optical Interface Card (Used In HI Series)
					 subbname02130965POWER(536680),            -- 02130965POWER
					 subbname02310GBMPOWER(536681),            -- 02310GBMPOWER
					 subbnameLS520G8S(536682),            -- S5700 LS520G8S 8-Port GE SFP Optical Interface Card 2*1
					 subbnameLS520G8T(536683),            -- S5700 LS520G8T 8-Port GE RJ45 Interface Card 2*1
					 subbnameLS521VST(536684),            -- S5700 LS521VST Stack Card 1*1

					 subbnameCX6D0L2XFA10(536685),        -- 2-Port 10GBase LAN/WAN-SFP+ Flexible Card A(S50-A,Occupy one sub-slot)
					 subbnameCX02317465POWER(536686),      -- 02317465POWER,500w POE
					 subbname8090DEVCX67P4CF0(536687),     --4-Port OC-3c/STM-1c POS Flexible Interface Card
					 subbname8090DEVCX6D00C2CF10(536688),  -- 2-Port Channelized OC-3c/STM-1c POS-SFP Flexible Card
					 subbname8090DEVCX6D00L1XX10(536689),  --1-Port 10GBase LAN/WAN-XFP Flexible Card
					 subbname8090DEVCX6D00EBGF10(536690),  --12-Port 100/1000Base-X-SFP Flexible Card
					 subbname8090DEVCX6D00EEGE10(536691),  --20-Port 10/100/1000Base-RJ45 Flexible Card
					 subbname8090DEVCX6D00L2XX10(536692),   --2-Port 10GBase LAN/WAN-XFP Flexible Card
					 subbname8090DEVCX6D00EFGF10(536693),  --24-Port 100/1000Base-X-SFP Flexible Card
					 subbname8090DEVCX6D0EBGFA11(536694),  --12-Port 100/1000Base-X-SFP Flexible Card A(S40-A,Supporting 1588v2)
					 subbname8090DEVCX62L1XEAGB0(536695),  --1-Port 10GBase LAN/WAN-XFP+10-Port 100/1000Base-X-SFP Flexible Card A(S40-A,Supporting 1588v2)
					 subbname8090DEVCR5D00E4GF70(536696),  --4-Port 100/1000Base-X-SFP High-speed Interface Card(HIC)
					 subbnameES5D21X02S00(536697),         --2-Port GE SFP or 10GE SFP+ Optical Interface Card

					 subbname02317465POWER(536700),        -- 02317465POWER
					 subbname02310JFDPOWER(536701),        -- 02310JFDPOWER
					 subbname02310JFAPOWER(536702),        -- 02310JFAPOWER
					 subbname8090DEVCX6D00P8HF10(536703),  --8-Port OC-12c/STM-4c POS-SFP Flexible Card
					 subbname8090DEVCX6D00P4CF10(536704),   --4-Port OC-3c/STM-1c POS-SFP Flexible Card
					 subbname8090DEVCX6D00P8CF10(536705),  --8-Port OC-3c/STM-1c POS-SFP Flexible Card
					 subbname02310JWVPOWER(536706),        -- 02310JWVPOWER
					 subbname02130953POWER(536707),        -- 02130953POWER
					 subbname02130984POWER(536708),        -- 02130984POWER
					 subbname02310CNKPOWER(536709),        -- 02310CNKPOWER
					 subbname02130966POWER(536710),        -- 02130966POWER
					 subbnameES5D21G16S00(536711),          -- ES5D21G16S00 16-Port GE SFP Optical Interface Card
					 subbnameES5D21G16T00(536712),          -- ES5D21G16T00 16-Port GE RJ45 Interface Card
					 subbnameES5D21L04Q00(536713),          -- ES5D21L04Q00 4-Port 40GE QSFP+ Optical Interface Card
					 subbnameES5D21X04S00(536714),          -- ES5D21X04S00 4-Port 10GE SFP+ Optical Interface Card
					 subbnameLS5D21G08S00(536715),          -- LS5D21G08S00 8-Port GE SFP Optical Interface Card(Used In S5310 EI Series)
					 subbnameLS5D21G08T00(536716),          -- LS5D21G08T00 8-Port GE RJ45 Interface Card(Used In S5310 EI Series)
					 subbnameCX67P4CFA(536717),             -- CX67P4CFA 4-Port OC-3c/STM-1c POS-SFP Flexible Interface Card
					 subbnameCX68L4XF(536718),              -- CX68L4XF 4-Port 10GBase-X-SFP+High-speed Interface Card
					 subbnameCX68L1XE8GF(536719),           -- CX68L1XE8GF 1-Port 10GBase-X-SFP+ + 8-Port 100/1000Base-X-SFP High-speed Interface Card
					 subbname02130971POWER(536720),         -- 02130971POWER

					 -- For  CX600  V8R5  CH  (536730~)
					 subbname8090DEVCX6D00L2XF10(536730),   -- CX68L2XFB, 2-Port 10GBase LAN/WAN-SFP+ Service Interface Card(SIC)
					 subbname8090DEVCX6D00E8GF10(536731),   -- CX68E8GFC, 8-Port 100/1000Base-X-SFP Service Interface Card(SIC)
					 subbname8090DEVCX6D00E8GE10(536732),   -- CX68E8GEB, 8-Port 10/100/1000Base-RJ45 Service Interface Card(SIC)

					 subbname8090DEVCX6D00C4CF11(536733),   -- CX68C4CF,  4-Port Channelized STM-1c POS-SFP Service Interface Card(SIC)
					 subbname8090DEVCX6D000IE110(536734),   -- CX68MIE1,  32-Port E1 Service Interface Card(SIC,75ohm)
					 subbname8090DEVCX6D000IE111(536735),   -- CX68MIE1B, 32-Port E1 Service Interface Card(SIC,120ohm)
					 subbname8090DEVCX6D000DE110(536736),   -- CX68MDE1A, 16-Port E1 Service Interface Card(SIC,75ohm)
					 subbname8090DEVCX6D000DE111(536737),   -- CX68MDE1B, 16-Port E1 Service Interface Card(SIC,120ohm)
					 subbname8090DEVCX6D00L4XF10(536739),   -- CX68L4XF, 4-Port 10GBase-X-SFP+High-speed Interface Card(SIC)
					 subbname8090DEVCX6DL1XE8G10(536740),   -- CX68L1XE8GF, 1-Port 10GBase LAN/WAN-SFP+  8-Port 100/1000Base-X-SFP Service Interface Card(SIC)
					 subbnameSwitchBAT4AHA(536741),         -- BAT-4AHA Lithiumion battery unit
					 subbnameSwitchBAT8AHA(536742),         -- BAT-8AHA Lithiumion battery unit
					 subbnameSwitchPBB12AHA (536743),       -- PBB-12AHA(12AH Power Backup Interface Card)
					 subbnameLS5D21G16S00(536744),          -- 16-Port GE SFP Optical Interface Card
					 subbnameLS5D21G16T00(536745),          -- 16-Port GE RJ45 Interface Card
					 subbnameLS5D21L04Q00(536746),          -- 4-Port 40GE QSFP+ Optical Interface Card
					 subbnameLS5D21X04S00(536747),          -- 4-Port 10GE SFP+ Optical Interface Card
					 subbname02131063POWER(536748),         -- 350W AC Power Module
					 subbname02131064POWER(536749),         -- 1150W AC Power Module
					 subbname02356618FAN(536750),           -- Fan box(EF,Airflow Port side to power supply side)
					 subbnameES5D21X04S01(536751),          -- 4 10 Gig SFP+ Interface Card(used in S5720HI series)
					 subbnameES5D21VST000(536752),          -- Dedicated stack interface card(uesed QSFP interface,used in S5720HI series)
					 subbname02310PQNPOWER(536753),         -- 350W DC Power Module
					 subbname02355338FAN(536754),           -- Fan box(EA,Back to Front)

					 subbnameES5D21X02S01(536755),          -- 2 10 Gig SFP+ Interface Card(used in S5720EI series)
					 subbnameLS5D21X02S01(536756),          -- 2 10 Gig SFP+ Interface Card(used in S5320EI series)
					 subbnameES5D21X02T01(536757),          -- 2 10 Gig RJ45 Interface Card(used in S5720EI series)
					 subbnameLS5D21X02T01(536758),          -- 2 10 Gig RJ45 Interface Card(used in S5320EI series)
					 subbnameES5D21X04S02(536759),          -- 4 10 Gig SFP+ Interface Card(used in S5720EI series)
					 subbnameLS5D21X04S02(536760),          -- 4 10 Gig SFP+ Interface Card(used in S5320EI series)
					 subbnameLS5D21VST000(536761),          -- Dedicated stack interface card(uesed QSFP interface,used in S5320EI series)
					 subbnameFAN028AB(536762),              -- Fan box(F,FAN panel side intake)
					 subbnameFAN028BB(536763),              -- Fan box(F,FAN panel side intake)
					 subbnamePDC650WABEPOWER(536764),       -- DC-DC Module,650W
					 subbnamePDC650WBBEPOWER(536765),       -- DC-DC Module,650W
					 subbnamePAC600WCBPOWER(536766),        -- 600W AC Power Module
					 subbnamePDC350WCBPOWER(536767),        -- 350W DC Power Module

										  --BEGIN: for CX600(CN) V8R7 by j00289303
				subbname8090DEVCX6D00EAGF10(536755),	-- CX68EAGFD, 10-Port 100/1000Base-X-SFP Service Interface Card(SIC)
				subbname8090DEVCX6DL1XE8G11(536756),	-- CX68L1XE8GFB, 1-Port 10GBase LAN/WAN-SFP+ + 8-Port 100/1000Base-X-SFP Service Interface Card(SIC)
				subbname8090DEVCX6D00E8GE11(536757),	-- CX68E8GED, 8-Port 100/1000Base-RJ45 Service Interface Card(SIC)
				subbname8090DEVCX6D00L4XF11(536758),	-- CX68L4XFD, 4-Port 10GBase LAN/WAN-SFP+ Service Interface Card(SIC)
				subbname8090DEVCX6D00L2XF11(536759),	-- CX68L2XFC, 2-Port 10GBase LAN/WAN-SFP+ Service Interface Card(SIC)
				--END: for CX600(CN) V8R7 by j00289303

-- 8090
					 subbname8090CFCARD(561151),         --CFCARD in MPUA or CFCARD2 in SRUA/MPUB
					 subbname8090Unkown(561152),          --
					 subbname8090E1XZ(561153),          --1*10GE LAN Single-mode Optical Interface LPU
					 subbname8090W1XZ(561154),          --1*10GE WAN Single-mode Optical Interface LPU
					 subbname8090EAGF(561155),          --10-port GbE SFP Optical Interface LPU
					 subbname8090P4UF(561156),          --4-port 2.5G POS SFP Optical Interface LPU
					 subbname8090GE(561157),            --GE card
					 subbname8090FE(561158),            --Fe card
					 subbname8090P1XZ(561159),          --1*OC-192c/STM-64c POS Optical Interface LPU
					 subbname8090Pos622(561160),        -- Pos_622
					 subbname8090Pos25G(561161),        -- Pos_2.5G
					 subbname8090ATM(561162),           --ATM
					 subbname8090DPT25G(561163),        -- DPT 2.5G
					 subbname8090P16X155Channel(561164),-- POS_16x155_CHANNEL
					 subbname8090P4HF(561165),          -- POS_4X622
					 subbname8090Pos155(561166),        -- POS_155
					 subbname8090E2XX(561167),          --2*10GBase LAN-XFP Optical Interface LPU C
					 subbname8090W2XX(561168),          --2*10GBase WAN-XFP Optical Interface LPU C
					 subbname8090P2XX(561169),          --2*OC-192c/STM-64c POS-XFP Optical Interface LPU C
					 subbname8090EMGE(561170),          --48*10/100/1000Base-TX-RJ45 Electrical Interface LPU
					 subbname8090A8CF(561171),          --ATM8X155M
					 subbname8090RPR10G(561172),        --RPR_1X_10G_CARD
					 subbname8090P8CF(561173),          --8*OC-3c/STM-1 POS-SFP Optical Interface LPU
					 subbname8090EFGE(561174),          --24*10/100/1000Base-TX-RJ45 Electrical Interface LPU

					 subbnameRNRPOS4X155(561175),          --4*OC-3c/STM-1 POS-SFP Optical Interface LPU
					 subbnameRNRPOS1X622(561176),          --1 Port 622M POS Interface LPU
					 subbnameRNRPOS1X25G(561177),          --1 Port 2.5G POS Interface LPU
					 subbnameRNRPOS16X155(561178),         --16*OC-3c/STM-1 POS-SFP Optical Interface LPU
					 subbnameRNRPOS4X622(561179),          --4 Port 622M POS Interface LPU
					 subbnameRNRPOS8X155(561180),          --8*OC-3c/STM-1 POS-SFP Optical Interface LPU
					 subbnameRNRATM8X155(561181),          -- 8 Port 155M ATM Interface LPU
					 subbnameRNRATM2X622(561182),          -- 2 Port 622M ATM Interface LPU

					 subbnameRNRETH4X100D(561183),        -- 4 Port 100M RJ45 Interface LPU
					 subbnameRNRETH4X100G(561184),        -- 4 Port 100M Fiber Interface LPU

					 subbnameRNRETH8X100D(561185),        -- 8 Port 100M RJ45 Interface LPU
					 subbnameRNRETH8X100G(561186),        -- 8 Port 100M Fiber Interface LPU

					 subbnameRNRETH16X100D(561187),       -- 16 Port 100M RJ45 Interface LPU
					 subbnameRNRETH16X100G(561188),       -- 16 Port 100M Fiber Interface LPU

					 subbnameRNRETH16X100OTHER(561189),   -- 16 Port 100M Interface LPU

					 subbnameRNRETH4XGE(561190),           -- 4 Port GE RJ45/Fiber Interface LPU
					 subbnameRNRETH4XGC(561191),           -- 4 Port GE GE_BIC RJ45/Fiber Interface LPU

					 subbnameRNRETH2XGE(561192),           -- 2 Port GE Interface LPU
					 subbnameRNRETH2XGC(561193),           -- 2 Port GE GE_BIC Interface LPU

					 subbnameRNRDPTCARD(561194),           --FRR Card

					 subbnameRNRCE1PDH2M(561195),        -- 8
					 subbnameRNRCT1PDH1P5M(561196),      -- 8

					 subbnameRNRE1PDH2M(561197) ,        -- 8
					 subbnameRNRE3PDH34M(561198),        -- 3
					 subbnameRNRT3PDH44M(561199),        -- 3

					 subbnameRNRCPOSOC3(561200),          --1
					 subbnameRNRPOSOC12C(561201),         --4
					 subbnameRNRPOSOC48C(561202),         --1

					 subbname8090P1UF(561203),              --1-port 2.5G POS SFP Optical Interface LPU
					 subbname8090P2UF(561204),              --2-port 2.5G POS SFP Optical Interface LPU

					 subbnameRNRATMA8CFFF(561205),        --8 Port 155M ATM Interface LPU
					 subbnameRNRATMA2HFFF(561206),        --2 Port 622M ATM Interface LPU
					 subbnameRNRRPR1X25(561207),           --1 Port 2.5G SDH RPR

					 subbnameRNRPOSP4CFFF(561208),        --4 Port 155M POS
					 subbnameRNRETHE8FFF(561209),         --8 Port 100M Fiber Interface LPU
					 subbname8090EFGF(561210),               --24GE
					 subbname8090EMGF(561211),               --48GE
					 subbnameRNRCPOS2OC3(561212),          --2*CPOS OC-3/STM-1-SFP Optical
					 subbmaneRNRCPOS4OC3(561213),      --4*CPOS OC-3/STM-1-SFP Optical
					 subbmaneRNR8XCE1(561214),          --UR-PIM-8xCHE1-RJ45
					 subbmaneRNRCPOSOC3FR(561215),    --1*CPOS OC-3/STM-1-SFP Optical
					 subbmaneRNR8XCT1(561216),          --UR-PIM-8xCHT1-RJ45
					 subbname8090R2UF(561217),               --2 Port 2.5G SDH RPR
					 subbname8090R4UF(561218),               --4 Port 2.5G SDH RPR

					 subbname8090R2GF(561219),               --2 Port GE RPR
					 subbname8090R4GF(561220),               --4 Port GE RPR
					 subbname8090EFFF(561221),               --24-port GE/FE SFP Phyiscal Interface Card

					 subbname8090CR53P1XX(561222),               --1-port 10G POS XFP  Flexible Pluggable Interface Daughter Card
					 subbname8090CR53E8GF(561223),               --8-port GE SFP Flexible Pluggable  Interface Daughter Card
					 subbname8090CR53E8FF(561224),               --8-port FE SFP  Flexible Pluggable  Interface Daughter Card
					 subbname8090CR53P1UF(561225),               --1-port 2.5G POS SFP Flexible Pluggable Interface Daughter Card
					 subbname8090CR53A2HF(561226),               --2-port 622M ATM  SFP  Flexible Pluggable Interface Daughter Card
					 subbname8090CR53A4CF(561227),               --4-port 155M ATM  SFP  Flexible Pluggable Interface Daughter Card

					 subbname8090L1XX0(561228),              --1-port 10GBase WAN/LAN XFP Flexible Interface Daughter Card
					 subbname8090EBGF(561229),               --12ports 100Base-FX/1000Base-X
					 subbname8090EBGE(561230),                --12ports 10Base-T/100Base-TX/1000Base-T

					 subbname8090EAGF2(561231),               -- 5 port GbE SFP Optical Interface LPU
				 subbname8090P4CF(561232),               -- 4*OC-3c/STM-1 POS-SFP Optical Interface LPU

					subbname8090L4XX(561233),    -- 4-port 10G LAN/WAN XFP Optical Interface Daughter Card,1*1
					subbname8090EKGE(561234),    -- 40-port 10/100/1000M RJ-45 Interface Daughter Card,1*1
					subbname8090EKGF(561235),    -- 40-Port FE/GE SFP Optical Interface Daughter Card,1*1
					subbname8090P2UFZ(561236),   -- 2-port 2.5G POS SFP Flexible Pluggable Interface Daughter Card, 1*1
				  subbname8090P4UFZ(561237),   -- 4-port 2.5G POS SFP Flexible Pluggable Interface Daughter Card, 1*1
				  subbname8090P4HFZ(561238),   -- 4-port 622M POS SFP Flexible Pluggable Interface Daughter Card, 1*1
				subbname8090P8HFZ(561239),   -- 8-port 622M POS SFP Flexible Pluggable Interface Daughter Card, 1*1
				subbname8090P4CFZ(561240),   -- 4-port 155M POS SFP Flexible Pluggable Interface Daughter Card, 1*1
				subbname8090P8CFZ(561241),   -- 8-port 155M POS SFP Flexible Pluggable Interface Daughter Card, 1*1
				 subbname8090C2CF(561242) ,    -- 2-Port Channelized OC-3c/STM-1c POS-SFP Flexible Card
				 subbname80904E3CT3(561243),  -- 4-Port Clear Channel E3/Channelized T3-SMB Flexible Card
				 subbname80908CE1CT1(561244), -- 8-Port Channelized E1/T1-RJ45 Flexible Card
				 subbname8090P1XXB(561245),    -- 1 port OC-192c/STM-64c POS-XFP Flexible Card
				 subbname8090OFCA(561246),               -- Cluster Optical Flexible Card A
				subbname8090CR53P1MZ(561247),               --1-port 40G POS XFP  Flexible Pluggable Interface Daughter Card
				subbname809055EMFE(561248),  -- 48-Port 10/100Base-TX-Delander Flexible Card
				subbname8090CR53E4XX(561249),               --4-port Eth Interface Daughter Card
				subbname8090CR52CKGFY(561250),   --40-port GF card
				subbname8090CR52EBGFB(561251),   --12-port GF card
				subbname8090CR52L1XXB(561252),   --1-port 10G LAN/WAN card
				subbname8090CR53D1MV(561253),               --1-port 40G WDM POS XFP  Flexible Pluggable Interface Daughter Card
				subbname8090CR53E8GFB(561254),   --8-port 100/1000Base-X SFP Flexible Interface Daughter Card
				subbname8090CR52EEGFN(561255),   --20-Port 100/1000Base-X-SFP Flexible Card
				subbname8090CR52EEGFNB(561256),  --20-Port 100/1000Base-X-SFP Flexible Card B
				subbname8090CR52L2XXN(561257),   --2-Port 10GBase WAN/LAN-XFP Flexible Card
				subbname8090CR52L2XXNB(561258),  --2-Port 10GBase WAN/LAN-XFP Flexible Card B
				subbname8090CR52L2XEEG(561259),  --2-Port 10GBase WAN/LAN-XFP and 20-Port 100/1000Base-X-SFP Flexible Card
				subbname8090CR52L2XEEGB(561260), ---2-Port 10GBase WAN/LAN-XFP and 20-Port 100/1000Base-X-SFP Flexible Card B
				subbname8090CR53A4CFB(561261),   ---4-Port OC-3c/STM-1c ATM-SFP Flexible Card
					 subbname8090ME03E1XX(561262),     ---1-Port 10G Ethernet LAN Card on LPUF-21
					 subbname8090ME03EAGF(561263),     ---10-Port Gigabit Ethernet Card on LPUF-21
					 subbname8090CR55OFC40(561264),     ---40G  Cluster Optical Flexible Card
				subbname8090CR52EKGFY(561265),        --40-port 1000Base-X-SFP card
				 subbname8090ME03E6GFE(561266),        ---6-Port 1000Base-SFP Flexible Card E
				 subbname8090CR55OFC100A(561267),      ---100G Cluster Optical Flexible Card A
			subbname8090CR55OFC100B(561268),      ---100G Cluster Optical Flexible Card B

					 subbname8090DEVCR57F4EFGF(561269),    --LPUF-40/41 24*GE SFP Optical Flexible Card, no 1588
					 subbname8090DEVCR57F4L4XX(561270),    --LPUF-40/41 4*10GE convergence Flexible Card, no 1588
					 subbname8090DEVCR57P2XXB(561271),     --LPUF-40/41 2*10G POS 1/2 width
					 subbname8090DEVCR56L5XX(561272),      --LPUF-100/101 5*10GE 1/2 width, support 1588
					 subbname8090DEVCR56L2XX(561273),      --LPUF-100/101 2*10GE 1/4 width, support 1588
					 subbname8090DEVCR56D2XX(561274),      --LPUF-100/101 2*10G POS/OTN 1/4
					 subbname8090DEVCR56P1MZ(561275),      --LPUF-100/101 1*40G POS 1/2
					 subbname8090DEVCR56E4XF(561276),      --LPUF-101 4*10GE 1/4 width convergence, no 1588
					 subbname8090DEVCR57EMGF(561277),      --LPUF-101 48*10GE 1/2 width BIDI, no 1588
					 subbname8090DEVCR57EEGE(561278),      --LPUF-40/41 20*GE RJ45 1/2 width, no 1588
					 subbname8090DEVCR56E1NC(561279),      --LPUF-101 1*100GE, test only
					 subbname8090DEVCR57L2XXY(561280),     --LPUF-40/41 2*10GE TM card, support BRAS HQOS
					 subbname8090DEVCR57EEGFY(561281),     --LPUF-40/41 20*GE TM card, support BRAS HQOS
					 subbname8090DEVCR56P2XX(561282),      --LPUF-100/101 2*10G POS 1/4 width
					 subbname8090DEVCR57EEGFB(561283),     --LPUF-41 20*GE SFP Optical card, 1/2 width, support 1588 and Y.1731
					 subbname8090DEVCR57EFGF(561284),      --LPUF-100 24*GE SFP Optical card, 1/2 width, no 1588
					 subbname8090DEVCR53L2XFA(561285),     --LPUF-50 2*10GE SFP Optical card,Support 1588
					 subbname8090DEVCR57L5XF(561286),      --LPUF-101 5*10GE SFP+ Optical card, 1/2 width, no 1588
					 subbname8090DEVCR57L2XXY1(561287),    --LPUF-40/41 2*10GE DPI card
					 subbname8090DEVCR5D0L2XFA70(561288),  --2-Port 10GBase LAN/WAN-SFP+ Flexible Card A(P50-A,Occupy one sub-slot)
					 subbname8090DEVCR57L1XEAG(561289),     --LPUF-41 1*10GE LAN/WAN XFP + 10*GE SFP Optical card, support 1588
					 subbname8090CR5M0L1XXB20(561290),     --1-Port 10GBase LAN/WAN-XFP Flexible Card B(P20-B)
					 subbname8090DEVCR56E1NCC(561291),     --CR56E1NCC0,1-Port 100GBase-CFP Flexible Card(NE5000E LPUF-200,2 sub-slots)
					 subbname8090DEVCR56E1MC(561292),      --CR56E1MCA0,1-Port 40GBase-CFP Flexible Card(NE5000E LPUF-100,2 sub-slots)
					 subbname8090DEVCR56LAXFA(561293),     --CR56L5XXA0,5-Port 10GBase LAN/WAN-XFP Flexible Card(CP100,2 sub-slots)
					 subbname8090DEVCR5D00E8GF70(561294),  --CX600,CX67E8GF0,8-Port 100/1000Base-X-SFP High-speed Interface Card(HIC)
					 subbname8090DEVCR5D0E8GFA70(561295),  --CX600,CX67E8GFB0,8-Port 100/1000Base-X-SFP High-speed Interface Card (HIC,Supporting 1588v2)
					 subbname8090DEVCR5D00E8FE10(561296),  --CX600,CX67E8FE0,8-Port 100Base-X-RJ45 Flexible Interface Card (FIC,Supporting 1588v2)
					 subbname8090DEVCR5D00E8FF10(561297),  --CX600,CX67E8FF0,8-Port 100Base-X-SFP Flexible Interface Card(FIC,Supporting 1588v2)
					 subbname8090DEVCR5D00C1CF10(561298),  --CX600,CX67C1CF0,1-Port Channelized OC-3c/STM-1c POS-SFP Flexible Interface Card (FIC)
					 subbname8090DEVCR5D000DE111(561299),  --CX600,CX67DE1A0,16-Port E1 Flexible Interface Card(FIC,120ohm)
					 subbname8090DEVCR5D000DE110(561300),  --CX600,CX67DE10,16-Port E1 Flexible Interface Card(FIC,75ohm)
					 subbname8090DEVCR5M0L5XFA71(561301),   --5-Port 10GBase LAN/WAN-SFP+ Flexible Card(P101-A,Occupy two sub-slots)
					 subbname8090DEVCR5D00E2NC70(561302),   --2-Port 100GBase LAN-CFP Integrated Line Processing Unit (LPUI-200)
					 subbname8090DEVCR5D00LEXF70(561303),   --20-Port 10GBase LAN/WAN-SFP+ Integrated Line Processing Unit (LPUI-200)
					 subbname8090DEVCR5D00E2NC71(561304),   --2-Port 100GBase LAN-CFP Integrated Line Processing Unit (LPUS-200)
					 subbname8090DEVCR5D00LEXF71(561305),   --20-Port 10GBase LAN/WAN-SFP+ Integrated Line Processing Unit (LPUS-200)
					 subbname8090DEVCX6D0L2XFA10(561306),   --2-Port 10GBase LAN/WAN-SFP+ Flexible Card A(S50-A)
					 subbname8090DEVCX6D0L5XFA10(561307),   --5-Port 10GBase LAN/WAN-SFP+ Flexible Card A(S51-A,Occupy two sub-slots)
					 subbname8090DEVCX6D0L2XFA11(561308),   --2-Port 10GBase LAN/WAN-SFP+ Flexible Card A(S51-A)
					 subbname8090DEVCX6D0L5XFA11(561309),   --5-Port 10GBase LAN/WAN-SFP+ Integrated Integrated Service Unit (ISUI-51,Supporting 1588v2,40Gbps is enabled by default)
					 subbname8090DEVCX6D0EMGFA10(561310),   --48-Port 100/1000Base-X-SFP Integrated Integrated Service Unit (ISUI-51,Supporting 1588v2)
					 subbname8090DEVCX6DL2XEIG1A(561311),   --2-Port 10GBase LAN/WAN-SFP++32-Port 100/1000Base-X-SFP Integrated Integrated Service Unit (ISUI-51,Supporting 1588v2,40Gbps is enabled by default)
					 subbname8090DEVCX6D0L5XFA12(561312),   --5-Port 10GBase LAN/WAN-SFP+ Flexible Card A(S101-A,Occupy two sub-slots)
					 subbname8090DEVCX6D0EFGFA10(561313),   --24-Port 100/1000Base-X-SFP Flexible Card A(S51-A)
					 subbname8090DEVCX6D0LAXFA11(561314),   --10-Port 10GBase LAN/WAN-SFP+ Integrated Integrated Service Unit (ISUI-101,Supporting 1588v2)
					 subbname8090DEVCR5M00L2XF70(561315),   --2-Port 10GBase WAN/LAN-SFP+ Flexible Card A
					 subbname8090DEVCR5M00EFGF70(561316),   --24-Port 100/1000Base-SFP Flexible Card
					 subbname8090DEVCR5M00E5XF70(561317),   --5-Port 10GBase LAN/WAN-SFP+ Flexible Card A
					 subbname8090DEVCR5M00E2XF70(561318),   --2-Port 10GBase LAN/WAN-SFP+ Flexible Card A
					 subbname8090DEVCR5D00L5XF70(561319),   --5-Port 10GBase LAN/WAN-SFP+ Integrated Line Processing Unit (LPUI-51,Supporting 1588v2)
					 subbname8090DEVCR5D00L4XF70-LPUI(561320),   --4-Port 10GBase LAN/WAN-SFP+ Integrated Line Processing Unit (LPUI-51,Supporting 1588v2)
					 subbname8090DEVCR5D00EMGF70(561321),   --48-Port 100/1000Base-SFP  Integrated Line Processing Unit (LPUI-51,Supporting 1588v2)
					 subbname8090DEVCR5DEFGL2X70(561322),   --24-Port 100/1000Base-X-SFP 2-Port 10GBase LAN/WAN-X-SFP Integrated Line Processing Unit (LPUI-51,Supporting 1588v2)
					 subbname8090DEVCR5D00L5XF71(561323),   --5-Port 10GBase LAN/WAN-SFP+ Integrated Line Processing Unit (LPUS-51)
					 subbname8090DEVCR5D00L4XF71(561324),   --4-Port 10GBase LAN/WAN-SFP+ Integrated Line Processing Unit (LPUS-51)
					 subbname8090DEVCR5D00EMGF71(561325),   --48-Port 100/1000Base-SFP  Integrated Line Processing Unit (LPUS-51)
					 subbname8090DEVCR5DEFGL2X71(561326),   --24-Port 100/1000Base-X-SFP 2-Port 10GBase LAN/WAN-X-SFP Integrated Line Processing Unit (LPUS-51)
					 subbname8090DEVCR5M00EFGF10(561327),   --24-Port 100/1000Base-X-SFP Flexible Card(Occupy two sub-slots)
					 subbname8090DEVCR5M00L5XF71(561328),   --5-Port 10GBase LAN/WAN-SFP+ Flexible Card A(Supporting 1588v2)
					 subbname8090DEVCR5M00E1MC70(561329),   --1-Port 40GBase LAN-CFP Flexible Card (Supporting 1588v2)
					 subbname8090DEVCR5D00E2MC70(561330),   --2-Port 40GBase LAN-CFP Integrated Line Processing Unit (LPUI-101,Supporting 1588v2)
					 subbname8090DEVCR5D00LAXX72(561331),   --10-Port 10GBase LAN/WAN-XFP Integrated Line Processing Unit (LPUI-101,Supporting 1588v2)
					 subbname8090DEVCR5D00E2MC71(561332),   --2-Port 40GBase LAN-CFP Integrated Line Processing Unit (LPUI-101)
					 subbname8090DEVCR5D00LAXX73(561333),   --10-Port 10GBase LAN/WAN-XFP Integrated Line Processing Unit (LPUI-101)
					 subbname8090DEVVSUF80(561334),    --SPU2.0 Board Sub Card(VSUF80)
					 subbname8090DEVCR52OFCV(561335),       --Cluster Virtual Optical Card

					 -- for V800R003C00 Card SBOM
					 subbname8090DEVCR5D00P2XX60(561336),   -- 2-Port OC-192c/STM-64c POS/OTU2-XFP Flexible Card(Dynamic switch between POS and OTN)(CP100,1 sub-slot)
					 subbname8090DEVCR5D00L5XX60(561337),   -- 5-Port 10GBase LAN/WAN-XFP Flexible Card(CP100,2 sub-slots)
					 subbname8090DEVCR5D00E5XX60(561338),   -- 5-Port 10GBase LAN-XFP Flexible Card(CP100,2 sub-slots)
					 subbname8090DEVCR5D00L2XX60(561339),   -- 2-Port 10GBase LAN/WAN-XFP Flexible Card(CP100,1 sub-slot)
					 subbname8090DEVCR5D00E2XX60(561340),   -- 2-Port 10GBase LAN-XFP Flexible Card(CP100,1 sub-slot)
					 subbname8090DEVCR5D00EFGF60(561341),   -- 24-Port 100/1000Base-SFP Flexible Card(CP100,2 sub-slots)
					 subbname8090DEVCR5D00P1MZ60(561342),   -- 1-Port OC-768c/STM-256c POS-2KM-LC Flexible Card(CP100,2 sub-slots)
					 subbname8090DEVCR5M00E1MC60(561343),   -- 1-Port 40GBase-CFP Flexible Card(NE5000E LPUF-100,2 sub-slots)
					 subbname8090DEVCR5D0OFCA060(561344),   -- 100G Cluster Optical Flexible Card B
					 subbname8090DEVCR5M0OFCK050(561345),   -- 400G Cluster Optical Flexible Card A
					 subbname8090DEVCR55OFC400B(561413),   -- 400G Cluster Optical Flexible Card B
					 subbname8090DEVCR50OFC400C(561414),   -- 400G Cluster Optical Flexible Card C

					 -- from 561348 to 561393 is for V6R6 packing card
					 -- for NE40E
					 subbname8090DEVNE40ECR5D0L2XFA70(561348),   --2-Port 10GBase WAN/LAN-SFP+ Flexible Card A
					 subbname8090DEVCR5D00A8CF70(561349),   --8-Port OC-3c/STM-1c ATM-SFP Flexible Card
					 subbname8090DEVCR5D00C8CF71(561350),   --8-Port Channelized OC-3c/STM-1c POS-SFP Flexible Card
					 subbname8090DEVCR5D00C4CF70(561351),   --4-Port Channelized OC-3c/STM-1c POS-SFP Flexible Card
					 subbname8090DEVCR5D0EFGFA70(561352),   --24-Port 100/1000Base-X-SFP Flexible Card A(P51-A)
					 subbname8090DEVCR5D0L5XFA70(561353),   --5-Port 10GBase LAN/WAN-SFP+ Flexible Card A(P51-A, Occupy two slots)
					 subbname8090DEVCR5D0L2XFA71(561354),   --2-Port 10GBase LAN/WAN-SFP+ Flexible Card A(P51-A)
					 subbname8090DEVCR5D0L5XFA72(561355),   --5-Port 10GBase LAN/WAN-SFP+ Flexible Card A(P101-A,Occupy two sub-slots)
					 subbname8090DEVCR5D0EFGFA71(561356),   --24-Port 100/1000Base-X-SFP Flexible Card A(P101-A,Occupy two sub-slots)
					 subbname8090DEVCR5D00E1MC70(561357),   --1-Port 40GBase LAN-CFP Flexible Card (P101-A,Occupy two sub-slots)
					 subbname8090DEVCR57L5XFC0(561360),   --5-Port 10GBase LAN/WAN-SFP+ card
					 subbname8090DEVCR57L4XEBG0(561361),   --4-Port 10GBase LAN/WAN-SFP++12-Port 100/1000Base-X-SFP card
					 subbname8090DEVCR57L2XEIG0(561362),   --2-Port 10GBase LAN/WAN-SFP++32-Port 100/1000Base-X-SFP card
					 subbname8090DEVCR57EMGFC0(561363),   --48-Port 100/1000Base-X-SFP card
					 subbname8090DEVCR57EFGFC0(561364),   --24-Port 100/1000Base-X-SFP card
					 subbname8090DEVCR57L1XEDG0(561365),   --1-Port 10GBase LAN/WAN-SFP++16-Port 100/1000Base-X-SFP card
					 subbname8090DEVCR57L4XFC0(561367),   --4-Port 10GBase LAN/WAN-XFP card
					 subbname8090DEVCR57L2XEEGB0(561368),   --2-Port 10GBase LAN/WAN-XFP+20-Port 100/1000Base-X-SFP card
					 subbname8090DEVCR57EKGFD0(561369),   --40-Port 100/1000Base-X-SFP card
					 subbname8090DEVCR57L4XFB2(561370),   --4-Port 10GBase LAN/WAN-SFP+ Card (Occupy two slots)
					 subbname8090DEVCR57L5XFB2(561371),   --5-Port 10GBase LAN/WAN-SFP+ Card (Occupy two slots)
					 subbname8090DEVCR57EFGFB2(561372),   --24-Port 100/1000Base-X-SFP Card
					 subbname8090DEVCR57L2XFB2(561373),   --2-Port 10GBase LAN/WAN-SFP+ Card
					 subbname8090DEVCR57E1MCB2(561374),   --1-Port 40GBase LAN-CFP card
					 subbname8090DEVCR57E1NC0(561375),    --1-Port 100GBase-CFP card

					 --V6R7 card packing NE&oversea CX
					 subbname8090DEVCR57EIGF0(561376),        --32 Ports FE/GE card
					 subbname8090DEVCR5D0L2XFE70(561377),     --2-Port 10GBase LAN/WAN-SFP+ Flexible Card E(P51-E)
					 subbname8090DEVCR5D0L5XFE70(561378),     --5-Port 10GBase LAN/WAN-SFP+ Flexible Card E(P51-E, Occupy two slots)
					 subbname8090DEVCR5D0EEGEA70(561379),     --20-Port 10/100/1000Base-RJ45 Flexible Card(P51-A)
					 subbname8090DEVCR5D0L5XFE71(561380),     --5-Port 10GBase LAN/WAN-SFP+ Flexible Card E(P101-E)
					 subbname8090DEVCR5D00LBXF72(561381),     --12-Port 10GBase LAN/WAN-SFP+ Flexible Card A(P120-A)
					 subbname8090DEVCR5D0L6XFA70(561382),     --6-Port 10GBase LAN/WAN-SFP+ Flexible Card A(P101-A)
					 subbname8090DEVCR5D00E1NC75(561383),     --1-Port 100GBase-CFP Flexible Card (P120)
					 subbname8090DEVCR5D00LBXF71(561384),     --12-Port 10GBase LAN/WAN-SFP+ Flexible Card A(P240-A)



					 -- for CX600 local
					 subbname8090DEVLOCALCX6D0L2XFA10(561385),   --2-Port 10GBase LAN WAN-SFP+ Flexible Card A(S50-A)
					 subbname8090DEVCX6D00A8CF10(561386),   --8-Port OC-3c STM-1c ATM-SFP Flexible Card(S50)
					 subbname8090DEVCX6D00C8CF10(561387),   --8-Port Channelized OC-3c/STM-1c POS-SFP Flexible Card(S50)
					 subbname8090DEVCX6D00C4CF10(561388),   --4-Port Channelized OC-3c/STM-1c POS-SFP Flexible Card(S50)
					 subbname8090DEVLOCALCX6D0EFGFA10(561389),   --24-Port 100 1000Base-X-SFP Flexible Card A(S51-A)
					 subbname8090DEVLOCALCX6D0L5XFA10(561390),   --5-Port 10GBase LAN WAN-SFP+ Flexible Card A(S51-A,Occupy two sub-slots)
					 subbname8090DEVLOCALCX6D0L2XFA11(561391),   --2-Port 10GBase LAN WAN-SFP+ Flexible Card A(S51-A)
					 subbname8090DEVLOCALCX6D0L5XFA12(561392),   --5-Port 10GBase LAN WAN-SFP+ Flexible Card A(S101-A,Occupy two sub-slots)
					 subbname8090DEVCX6D0EFGFA11(561393),   --24-Port 100/1000Base-X-SFP Flexible Card A(S101-A,Occupy two sub-slots)
					 subbname8090DEVVSUF160(561394),    --SPU2.0 Board Sub Card(VSUF160)

					 --for CX600 local(561398 is NE&oversea CX) V6R7 card packing
					 subbname8090DEVCX6D0EEGEA10(561395),     --20-Port 10/100/1000Base-RJ45 Flexible Card(S51-A)
					 subbname8090DEVCX6DISUFB010(561396),     --6-Port 10GBase LAN/WAN-SFP+ Flexible Card A(S120-A)
					 subbname8090DEVCX6D0LBXFA10(561397),     --12-Port 10GBase LAN/WAN-SFP+ Flexible Card A(S120-A)
					 subbname8090DEVCR5D00E1NC74(561398),     --1-Port 100GBase-CFP Flexible Card (P240)
					 subbname8090DEVCR5D0EFGFE70(561399),     --24-Port 1000Base-X-SFP Flexible Card E(P51-E)
					 subbname8090DEVL3XEFG7C(561400),         --3-Port 10GBase LAN/WAN-SFP+ Flexible Card A
					 subbname8090DEVCR57EFGFE2(561401),       --24-Port 1000Base-X-SFP Fixed Card E
					 subbname8090DEVCR57L2XFE2(561402),       --2-Port 10GBase LAN/WAN-SFP+ Fixed Card E
					 subbname8090DEVCR57L5XFE2(561403),       --5-Port 10GBase LAN/WAN-SFP+ Fixed Card E
					 subbname8090DEVCR57LBXF2(561404),        --12-port 10GBase LAN/WAN-SFP+ Fixed Card
					 subbname8090DEVCR57E1NCB2(561405),        --1-Port 100GBase-CFP Fixed Card
					 subbname8090DEVCR57L6XF0(561406),        --6-port 10GBase LAN/WAN-SFP+ Fixed Card

			  -- for NE5000E V800R005C01 Card SBOM
			  subbname8090DEVCR5D00E2NC61(561407),   -- 2-Port 100GEBase-CXP Flexible Card(CP400,1 sub-slot)
			  subbname8090DEVCR5D00E6MF61(561408),   -- 6-Port 40GBase-QSFP+ Flexible Card(CP400,1 sub-slot)
			  subbname8090DEVCR5D0OLEXF61(561409),   -- 20-Port 10GBase LAN-SFP+ Flexible Card(CP400,1 sub-slot)
			  subbname8090DEVCR5D00E1NC61(561410),   -- 1-Port 100GBase-CFP Flexible Card(CP400,1 sub-slots)
					 subbname8090DEVCR5D00L5XF60(561411),   -- 5-Port 10GBase LAN/WAN-SFP+ Flexible Card B(CP100,2 sub-slots)
		subbname8090DEVCR5D00E5XF60(561412),   -- 5-Port 10GBase LAN-SFP+ Flexible Card B(CP100,2 sub-slots)
		subbname8090DEVCR5D00N2NC61(561416),   -- 2-Port 100G OTN/ETH-CFP2 Flexible Card(CP400,Occupy 1 sub-slot)
		subbname8090DEVCR5D00E1NC62(561417),   -- 1-Port 100GBase-CFP Flexible Card(CP400,Occupy 1 sub-slot)

					 --for CX600 V8R5  OC and NE40E  (561500 ~)
					 subbname8090DEVCR5D00L2XF70(561500),   -- CX68L2XFB, 2-Port 10GBase LAN/WAN-SFP+  Physical Interface Card(PIC)
					 subbname8090DEVCR5D00E8GF71(561501),   -- CX68E8GFC, 8-Port 100/1000Base-X-SFP  Physical Interface Card(PIC)
					 subbname8090DEVCR5D00E8GE70(561502),   -- CX68E8GEB, 8-Port 10/100/1000Base-RJ45 Physical Interface Card(PIC)
					 subbname8090DEVCR5D00L1XE8GF70(561503), -- 1-Port 10GBase LAN/WAN-SFP+  8-Port 100/1000Base-X-SFP Physical Interface Card(PIC)
					 subbname8090DEVCR5D00C4CF71(561504),   -- CX68C4CF ,    4-Port Channelized STM-1c POS-SFP  Physical Interface Card(PIC)
					 subbname8090DEVCR5D000IE170(561505),   -- CX68MIE1 ,    32-Port E1 Physical Interface Card(PIC,75ohm)
					 subbname8090DEVCR5D000IE171(561506),   -- CX68MIE1B ,   32-Port E1 Physical Interface Card(PIC,120ohm)
					 subbname8090DEVCR5D000DE170(561507),   -- CX68MDE1A ,   16-Port E1 Physical Interface Card(PIC,75ohm)
					 subbname8090DEVCR5D000DE171(561508),   -- CX68MDE1B ,   16-Port E1 Physical Interface Card(PIC,120ohm)
					 subbname8090DEVCR5DL1XE8G70(561503), -- CX68L1XE8GF, 1-Port 10GBase LAN/WAN-SFP+  8-Port 100/1000Base-X-SFP Physical Interface Card(PIC)
					 subbname8090DEVCR5D00L4XF70(561509),   -- CX68L4XF, 4-Port 10GBase-X-SFP+High-speed Interface Card(PIC)
					 subbname8090DEVCR5D00P4CF70(561510),   -- CX67P4CFA, 4-Port OC-3c/STM-1c POS-SFP Flexible Interface Card(PIC)
					 subbname8090DEVCR5D00AUXQ10(561511),   -- CX67AUXQ, Auxiliary  Flexible Interface Card with 4-Port 100Base-RJ45 (FIC,Supporting 1588v2)(PIC)
			  subbname8090DEVCR5D00C4T370(561512),   -- CX68C4T3, 4-Port Clear Channel E3/Channelized T3 Physical Interface Card (PIC)
			  --BEGIN: for PTN6900 V6R8C10 by w00195304
			  subbname8090DEVTNR1EXL6(561513),       -- V6R8C10,03030WGU,3-Port 40GBase-QSFP+ Fixed Card
			  subbname600DEVCR57LAXFB(561514),       -- V6R8C10,03031AKC,10-Port 10GBase LAN/WAN-SFP+ Fixed Card
		--END: for PTN6900 V6R8C10 by w00195304

					 --BEGIN: for NE40E V8R6C00 by zhaowei 55681 (561530 ~)
					 subbname8090DEVCR5D0P8UF70(561530),      -- 8-Port OC-48c/STM-16c POS-SFP Flexible Card(P120)
					 --END: for NE40E V8R6C00 by zhaowei 55681

					 --BEGIN: for NE40E V8R6C10 by yinweilin 00249354
					 subbname8090DEVCR5D00LFXF74(561531),      -- CR57LFXFE, 24-Port 10GBase LAN/WAN-SFP+ Flexible Card A(P480-A)
					 subbname8090DEVCR5D00E2NC72(561532),      -- CR57E2NCE, 2-Port 100GBase-CFP2 Flexible Card A(P480-A)
					 subbname8090DEVCR57LFXFE1(561533),      -- 48-Port 10GBase LAN/WAN-SFP+ Integrated Line Processing Unit (LPUI-480)
					 subbname8090DEVCR57E2NCE1(561534),      -- 2-Port 100GBase-CFP2 + 24-Port 10GBase LAN/WAN-SFP+ Integrated Line Processing Unit (LPUI-480)
					 --END: for NE40E V8R6C10 by yinweilin 00249354

					 subbname8090DEVCR57E2NCE(561535),    -- 2-Port 100GBase-CFP2 Flexible Card A(P480-A)
					 subbname8090DEVCR57LFXFE(561536),    -- 24-Port 10GBase LAN/WAN-SFP+ Flexible Card A(P480-A)
					 subbname8090DEVCR57LEXFE(561537),    -- 20-Port 10GBase LAN/WAN-SFP+ Flexible Card
					 --BEGIN: add by l00242807 for v6r8c00 cx600
					 subbname8090DEVCX6D00A2HF10(561538),    -- 2-Port OC-12c/STM-4c ATM-SFP Flexible Card(S10)
					 --END: add by l00242807  for v6r8c00  cx600

				--BEGIN: for CX600(CN) V8R7 by j00289303
				subbname8090DEVCR5D0L2XFH71(561539),	-- CX68L2XFC, 2-Port 10GBase LAN/WAN-SFP+ Physical Interface Card H (PIC-H)
				subbname8090DEVCR5D0EAGFH70(561540),	-- CX68EAGFD, 10-Port 100/1000Base-X-SFP Physical Interface Card H (PIC-H)
				--END: for CX600(CN) V8R7 by j00289303
				--BEGIN: for PTN6900(oversea) V8R7 by j00289303
				subbname8090DEVCR5D00EAGF70(561541),	-- CX68EAGFD, 10-Port 100/1000Base-X-SFP Physical Interface Card(PIC)
				subbname8090DEVCR5DL1XE8G71(561542),	-- CX68L1XE8GFB, 1-Port 10GBase LAN/WAN-SFP+ + 8-Port 100/1000Base-X-SFP Physical Interface Card(PIC)
				subbname8090DEVCR5DP4C2HF70(561543),	-- CX68P4CFC, 4-Port OC-3c/STM-1c (or 2-Port OC12c/STM-4c)  POS-SFP Physical Interface Card(PIC)
				subbname8090DEVCR5D00E8GE71(561544),	-- CX68E8GED, 8-Port 100/1000Base-RJ45 Physical Interface Card(PIC)
				subbname8090DEVCR5D00L4XF712(561545),	-- CX68L4XFD, 4-Port 10GBase LAN/WAN-SFP+ Physical Interface Card(PIC)
				subbname8090DEVCR5D00L2XF71(561546),	-- CX68L2XFC, 2-Port 10GBase LAN/WAN-SFP+ Physical Interface Card(PIC)
				--END: for PTN6900(oversea) V8R7 by j00289303

					 --BEGIN: add by yangdi 00238145 for v6r8c10 NE40E
					 subbname8090DEVCR5D0E3MFA70(564768), -- 3-Port 40GBase-QSFP+ Flexible Card(P240-A)
					 subbname8090DEVCR5D00TBXF70(564769), -- 12-Port OTU2-SFP+ Flexible Card(P120)
					 subbname8090DEVCR5D00T6XF70(564770), -- 6-Port OTU2-SFP+ Flexible Card(P120)
					 subbname8090DEVCR5D00T1NV70(564771), -- 1-Port OTU4-80KM-LC Flexible Card A(P240-A)
					 subbname8090DEVCR5D0LAXFE70(564773), -- 10-Port 10GBase LAN/WAN-SFP+ Flexible Card E(P240-E)
					 --END: add by yangdi 00238145 for v6r8c10 NE40E

		--BEGIN: add by jiangwenjiang 00221556 for v6r8c20 NE40E
					 subbname8090DEVCR5D0L5XFH70(561430),   -- 5-Port 10GBase LAN/WAN-SFP+ Flexible Card H(P120-H)
		subbname8090DEVME0D0L5XFH7H(561431),   -- 5-Port 10GBase LAN/WAN-SFP+ Flexible Card H(BP100-H)
		subbname8090DEVCX6D0L5XFH10(561432),   -- 5-Port 10GBase LAN/WAN-SFP+ Flexible Card H(S102-H)
		subbname8090DEVCR5D0L2XFH70(561433),   -- 2-Port 10GBase LAN/WAN-SFP+ Flexible Card H(P51-H)
		subbname8090DEVME0D0L2XFH7H(561434),   -- 2-Port 10GBase LAN/WAN-SFP+ Flexible Card H(BP51-H)
		subbname8090DEVCR5D0L1XFA70(561435),   -- 1-Port 10GBase LAN/WAN-SFP+ Flexible Card A(P50-A)
		subbname8090DEVTNRD00MD8A70(561436),   -- 8-Channel CWDM Multiplexing & Demultiplexing Flexible Card
		subbname8090DEVCR5D00MD8A70(561437),   -- 8-Channel CWDM Multiplexing & Demultiplexing (1471/1491/1511/1531/1551/1571/1591/1611nm) Flexible Card(P50)
					 --END: add by jiangwenjiang 00221556 for v6r8c20 NE40E

-- ME60:
					 subbnameME60Unkown(159744),
					 subbnameME60P1XZE0(159745),        --ME60P1XZE0 Module
					 subbnameME60W1XQE0(159746),        --ME60W1XQE0 Module
					 subbnameME60W1XSE0(159747),        --ME60W1XSE0 Module
					 subbnameME60E1XQE0(159748),        --ME60E1XQE0 Module
					 subbnameME60E1XSE0(159749),        --ME60E1XSE0 Module
					 subbnameME60EAGFE0(159750),        --ME60EAGFE0 Module
					 subbnameME60P4UFE0(159751),        --ME60P4UFE0 Module
					 subbnameME60EAGFB0(159752),        --ME60EAGFB0 Module
					 subbnameME60P1XQE0(159753),        --ME60P1XQE0 Module
					 subbnameME60P1XVE0(159754),        --ME60P1XVE0 Module
					 subbnameME60E1XSB0(159755),        --ME60E1XSB0 Module
					 subbnameME60E1XQB0(159756),        --ME60E1XQB0 Module
					 subbnameME60W1XSB0(159757),        --ME60W1XSB0 Module
					 subbnameME60W1XQB0(159758),        --ME60W1XQB0 Module
					 subbnameME60EFGEB0(159759),        --ME60EFGEB0 Module

					 subbnameME60EFGFB0(159760),         --ME01EFGFB0 Module
					 subbnameME60E2XXB0(159761),         --ME01E2XXB0 Module
					 subbnameME60EAGFB1(159762),         --ME01EAGFB1 Module
					 subbnameME60E5GFB0(159763),         --ME01E5GFB0 Module
					 subbnameME60E1XXB0(159764),         --ME01E1XXB0 Module
					 subbnameME60P2XXM0(159765),         --ME01P2XXM0 Module
					 subbnameME60EFGFM0(159766),         --ME01EFGFM0 Module
					 subbnameME60EAGFM0(159767),         --ME01EAGFM0 Module
					 subbnameME60P8CFM0(159768),         --ME01P8CFM0 Module
					 subbnameME60P4HFM0(159769),         --ME01P4HFM0 Module
					 subbnameME60P4UFM0(159770),         --ME01P4UFM0 Module
					 subbnameME60E1XXM0(159771),         --ME01E1XXM0 Module
					 subbnameME60E2XXM0(159772),         --ME01E2XXM0 Module
					 subbnameME60P1XXM0(159773),         --ME01P1XXM0 Module

					 subbnameME60A4HFB0(159774),         --ME01A4HFB0 Module
					 subbnameME60AGCFB0(159775),         --ME01AGCFB0 Module
					 subbnameME60E4GFB0(159776),         --ME01E4GFB0 Module
					 subbnameME60EWFEB0(159777),         --ME01EWFEB0 Module
					 subbnameME60EGFFB0(159778),         --ME01EGFFB0 Module

					 subbnameME60EMGFB0(159779),         --ME01EMGFB0 Module
					 subbnameME60EMGFM0(159780),         --ME01EMGFM0 Module

					 subbnameME60EFFFB1(159781),         --24*1000Base SFP Light/Electrical Interface BSU line control board
					 subbnameME60EFFFM0(159782),          --24*1000Base SFP Light/Electrical Interface MSU line control board

					 subbnameME60EAGFYB0(159783),         --10*1GE SFP Light/Electrical Interface with TM  -1*1

					 subbnameME60A8CFB0(159784),         --ME60A8CFB0 Module
					 subbnameME60P8CFM1(159785),         --ME60P8CFM1 Module

					 subbnameME60E4XXB0(159786),         --ME60E4XXB0 Module
					 subbnameME60E4XXM0(159787),          --ME60E4XXM0 Module
					 subbnameME03EEGFE0(159792),         --LPUF-40/41 20*GE TM card, support BRAS HQOS
					 subbnameME03L5XFA0(159793),         --LPUF-101 5*10GE SFP+ Optical card, 1/2 width, no 1588
					 subbnameME03E1NC0(159794),          --LPUF-101 1*100GE, test only
					 subbnameME03P1MZ0(159795),          --1-port 40G POS XFP  Flexible Pluggable Interface Daughter Card
					 subbnameME03L2XXB0(159796),         --LPUF-40/41 2*10GE TM card, support BRAS HQOS
					 subbnameME03L2XXB1(159797),         --LPUF-40/41 2*10GE DPI card
					 subbnameME01A8CFB1(159799),         --ME01A8CFB1 Module
					 subbnameME60VSUF80(159800),           --SPU2.0 Board Sub Card(VSUF80)
					 subbnameME60VSUF160(159801),           --SPU2.0 Board Sub Card(VSUF160)

					 --V6R7 card packing ME60
					 subbnameME0D0EFGFB7H(159802),    --24-Port 100/1000Base-X-SFP Flexible Card(BP51)
					 subbnameME0D0L5XXB7F(159803),    --5-Port 10GBase WAN/LAN-XFP Flexible Card(BP51)
					 subbnameME0D0L2XXB7H(159804),    --2-Port 10GBase WAN/LAN-XFP Flexible Card(BP51)
					 subbnameME0D0EFGFE7H(159805),    --24-Port 1000Base-X-SFP Flexible Card E(BP51-E)
					 subbnameME0D0L5XXE7F(159806),    --5-Port 10GBase WAN/LAN-XFP Flexible Card E(BP51-E)
					 subbnameME0D0L2XXE7H(159807),    --2-Port 10GBase WAN/LAN-XFP Flexible Card E(BP51-E)
					 subbnameME0D0L6XXB7H(159808),    --6-Port 10GBase WAN/LAN-XFP Flexible Card(BP100)
					 subbnameME0D0L5XXB7H(159809),    --5-Port 10GBase WAN/LAN-XFP Flexible Card(BP100)
					 subbnameME0D0L5XXE7H(159810),    --5-Port 10GBase WAN/LAN-XFP Flexible Card E(BP100-E)
					 subbnameME0D0L1NXB7H(159811),    --1-Port 100GBase WAN/LAN-XFP Flexible Card(BP100)
					 subbnameME0D0LBXXB7H(159812),    --12-Port 10GBase WAN/LAN-XFP Flexible Card(BP240)
					 subbnameME0D2L1NXB7H(159813),    --1-Port 100GBase WAN/LAN-XFP Flexible Card(BP240)
					 --V6R8 card packing ME60
			  subbnameME0D0LBXXE7H(564729),    --12-Port 10GBase LAN/WAN-SFP+ Flexible Card E(BP240-E)


-- S9300:       0x000A1000~0x000A1fff(659456~663551)
					 subbnameLE01FSUA(659456),
					 subbnameLE0D00CKMA00(659457),          --Clock Pinch Board-1588
					 subbnameLE0MFSUA(659458),          --Flexible Service Unit
					 subbnameLE02CKMB(659459),           --Clock Pinch Board-BITS/1588
					 subbnameLE0D0VSTSA00(659460),
					 subbnameLE02S4USE(659461),
					 subbnameLE02TCAMA(659462),
					 subbnameCR53P1UF(659463),  --1-Port OC-48c/STM-16C POS SFP Flexible Pluggable Interface Daughter Card
					 subbnameCR53P4HF(659464),  --4-Port OC-12c/STM-4C POS SFP Flexible Card
					 subbnameCR53P4CF(659465),  --4-Port OC-3c/STM-1C POS SFP Flexible Card
					 subbnameCR53E8GF(659466), --8-Port FE/GE SFP Flexible Pluggable Interface Daughter Card
					 subnameLE2D2VS08000(659467), --8-Port 10G Cluster Switching System Service Unit (SFP+)
					 subbnameLE2D2SC86S00(659468), --x86 Service Process Sub-card

-- S7700:       0x000A2000~0x000A2fff(663552~667647)
					 subbnameES0D00FSUA00(663552),          --Flexible Service Unit

-- S9700:       0x000A7000~0x000A7fff(684032~688127)
					 subnameET1D2VS08000(684032), --8-Port 10G Cluster Switching System Service Unit (SFP+)


-- SSP & NSE:
					 subbnameNSESX11E8GF(231151),      --SX11E8GF1020
					 subbnameNSESX11P4UF(231152),      --SX11P4UF1020
					 subbnameNSESX11L1XX(231153),       --SX11L1XX2020
					 subbnameNSESX11EBGF(231154),      --SX11EBGF2020
					 subbnameNSESX11EBGE(231155),      --SX11EBGE2020
					 subbnameNSESX11P1XX(231156),      --SX11P1XX2020
					 virentSSP5000SX1D00P1MZ70(697000),     --virentSSP5000SX1D00P1MZ70
					 virentSSP5000SX1D00P2XX70(697001),     --virentSSP5000SX1D00P2XX70
					 virentSSP5000SX1D0L5XXA70(697002),     --virentSSP5000SX1D0L5XXA70
					 virentSSP5000SX1DP8XE8X70(697003),     --virentSSP5000SX1DP8XE8X70
					 virentSSP5000SX1DP2ME8X70(697004),     --virentSSP5000SX1DP2ME8X70
					 virentSSP5000SX1D00P8UF70(697005),     --virentSSP5000SX1D00P8UF70

-- atn
					 subbnameANTUnkown(225280),          --
					 subbnameAND1ML1(225465),        -- 16 Channels E1 Interface Board(75ohm)
					 subbnameAND1ML1A(225466),       -- 16 Channels E1 Interface Board(120ohm)
					 subbnameAND1CD1(225283),        -- 1 Channelized OC-3c/STM-1c Optical Interface Board
					 subbnameANE7E8GF(225284),       -- 8 Channels Gigabit Ethernet Optical/Electric High-speed Interface Board(HIB,No supporting 1588v2)
					 subbnameANE7E8GFA(225285),      -- 8 Channels Gigabit Ethernet Optical/Electric High-speed Interface Board A(HIB)
					 subbnameAND1EF8F(225286),       -- 8 Channels Fast Ethernet Optical Interface Board
					 subbnameAND1EF8T(225287),       -- 8 Channels Fast Ethernet Electric Interface Board
					 subbnameAND1AUXQ(225288),       -- Assistant Channel And 4 Channels FE Electric Interface Board
					 subbnameANE7A4CF(225289),       -- 4 Channels OC-3c/STM-1c ATM Optical Interface Board

--ATN910&950, ATN950B
--card
					subbnameATNAND1EG2(225453),        --2x GE service interface board
					subbnameATNAND1EG4F(225454),       --4x GE service interface board
					subbnameATNAND2ML1A(225455),       --16x E1 service interface board (75 ohms)
					subbnameATNAND2ML1B(225456),       --16x E1 service interface board (120 ohms)
					subbnameATNAND1MD1A(225457),       --32x E1 service interface board (75 ohms)
					subbnameATNAND1MD1B(225458),       --32x E1 service interface board (120 ohms)
					subbnameATNAND1SHD4(225460),       --4x G.SHDSL service interface board
					subbnameATNAND1SHD4I(225461),      --4x IMA mode of G.SHDSL service interface board
					subbnameATNAND1AVD8A(225462),      --8x ADSL2+/VDSL2 service interface board
					subbnameATNAND1EG4T(225463),       --4x GE service interface board electric
					subbnameATNAND1MO1C(225464),       --8x T1 service interface board electric(100 ohms)
					subbnameATNVIRTUAL(225459),        --Virtual card
					subbnameATNVIRTUAL1(225467),       --Virtual card(CXPI)
					subbnameATNVIRTUAL2(225490),       --Virtual card(910I),with 4GE(o),4GE/FE(o),4GE/FE(e)
					subbnameATNVIRTUAL3(225491),       --Virtual card(910I),with 16E1,4GE(o),4GE/FE(o),4GE/FE(e)
					subbnameATNVIRTUAL4(225492),       --Virtual card(910I),with 16E1,4GE(o),4GE/FE(o),4GE/FE(e),4FE
					subbnameATNVIRTUAL5(225500),       --Virtual card(910I),with 16E1,2GE(o)+4GE/FE(o),4GE/FE(e)
					subbnameATNVIRTUAL6(225516),       --Virtual card(910I),with 4GE(o),4GE/FE(o),4GE/FE(e),poe
					subbnameATNVIRTUAL7(225517),       --Virtual card(905),with 2Combo,2GE(o),2GE/FE(e)
					subbnameATNVIRTUAL8(225518),       --Virtual card(905),with 4GE(o)
					subbnameATNVIRTUAL9(225519),       --Virtual card(905),with 4GE(o),poe
					subbnameATNAND1EX1(225468),        --1x 10GE service interface board fiber
					subbnameATNAND1EM8F(225469),       --8x GE service interface board fiber
					subbnameATNAND1EM4F(225470),       --4x GE service interface board fiber
					subbnameATNAND1EM8T(225471),       --8x GE service interface board electric
					subbnameATNAND1EM4T(225472),       --4x GE service interface board electric
					subbnameATNAND3ML1A(225479),       --16x E1 service interface board (75 ohms)
					subbnameATNAND3ML1B(225480),       --16x E1 service interface board (120 ohms)
					subbnameATNAND2MD1A(225481),       --32x E1 service interface board (75 ohms)
					subbnameATNAND2MD1B(225482),       --32x E1 service interface board (120 ohms)
					subbnameATNAND2CQ1B(225497),       --4-port channelized OC-3c/STM-1c POS-SFP Flexible Interface Board
					subbnameAND2EG2(225504),           --2 GE service interface board
					subbnameAND2EF8F(225505),          --8 Channels Fast Ethernet Optical Interface Board
					subbnameAND2EF8T(225506),          --8 Channels Fast Ethernet Electric Interface Board
					subbnameAND1EM4C(225507),          --4 Channels GE/FE Combo Board
					subbnameATNAND2PQ10(225520),       --4 Channels OC-3/STM-1 POS Optical Interface Board
-- PTN:
					subbnameTN91EG20(229376),         --20-Port 100/1000Base-X-SFP Flexible Card(Supporting 1588v2)
					subbnameTN91EX2(229377),          --2-Port 10GBase LAN/WAN-XFP Flexible Card(Supporting 1588v2)
					subbnameTN91ET20B(229378),        --20-Port 10/100/1000Base-RJ45 Flexible Card
					subbnameTN91EG8(229379),          --8-Port 100/1000Base-X-SFP Flexible Card(Supporting 1588v2)
					subbnameTN91CD1(229380),          --2-Port Channelized OC-3c/STM-1c POS-SFP Flexible Card
					subbnameTN91MT1(229381),          --24-Port Channelized E1/T1-DB100 Flexible Card

					subbnameTNR1EG8(229382),          --8 Ports FE/GE (Optical) Ethernet Processing Flexible Card (Supporting 1588V2)
					subbnameTNR1CD1(229383),          --2 Ports Channelized OC-3C/STM-1C SFP Flexible Card
					subbnameTNR1MT1(229384),          --24 Ports Channelized E1/T1-DB100 Flexible Card
					subbnameTNR1EX2(229385),          --2 Ports 10 Gigabit Ethernet Processing Flexible Card (Supporting 1588V2)
					subbnameTNR1EG20(229386),         --20 Ports FE/GE (Optical) Ethernet Processing Flexible Card (Supporting 1588V2)
					subbnameTNR1ET20B(229387),        --20 Ports FE/GE (Electric) Ethernet Processing Flexible Card

					--for V6R6 CH-PTN card packing
					subbnameTNRD00EFF800(229405),     --8 Ports FE (Optical) Ethernet Processing Flexible Card (Supporting 1588v2)
					subbnameTNRD000EX201(229406),     --2 Ports 10 Gigabit Ethernet Processing Flexible Card (Supporting 1588v2)
					subbnameTNRD000EX500(229408),     --5 Ports 10 Gigabit Ethernet Processing Flexible Card (Supporting 1588v2)
					subbnameTNRD00EXL100(229500),     --1 Ports 40 Gigabit Ethernet Processing Flexible Card (Supporting 1588v2)
					subbnameTNRD000CO101(229501),     --8 Ports Channelized OC-3C/STM-1C SFP Flexible Card

					--for V6R6 PTN6900 chinamobile JICAI
					subbnameTNRD000CO100(229600),     --8 Ports Channelized OC-3C/STM-1C SFP Flexible Card
					subbnameTNRD000SO100(229602),     --8 Ports OC-3/STM-1 CFP Flexible Card

					--for V6R7 PTN6900 card packing
					subbnameTNRD000EX600(229700),     --6 Ports 10 Gigabit Ethernet Processing Flexible Card (Supporting 1588v2)
					subbnameTNRD000EH101(229702),     --1 Port 100 Gigabit Ethernet Processing Flexible Card (Supporting 1588v2)
					subbnameTNRD00EX1200(229703),     --12 Ports 10 Gigabit Ethernet Processing Flexible Card (Supporting 1588v2)
					subbnameTNRD00EXL300(229704),    --3 Ports 40GBase-CFP Ethernet Processing Board (Supporting 1588v2)

				-- V8R5 PTN packaging
				  subbnameTNRD00MPUK70(229450),     --for V8R5C01 TNRD00MPUK70(SBOM),Main Processing Unit K

-- AR:          0x000A3000~0x000A3fff(667648~671743)
					 subbnameAR01DD016A(667648),       --16 Channel DSP module
					 subbnameAR01DD032A(667649),       --32 Channel DSP module
					 subbnameAR01DD064A(667650),       --64 Channel DSP module
					 subbnameAR01DD128A(667651),       --128 Channel DSP module
					 subbnameAR01WiFi(667652),         --WiFi module
					 subbnameAR013G(667653),           --3G module
					 subbnameAR01FAN(667654),            --FAN module for AR1220
-- NE20E-X6:
					subbnameCR2D00P1XX11(675840),     --1-Port OC-192c/STM-64c POS-XFP Flexible Card(HIC20)
					subbnameCR2D00L1XX10(675841),     --1-Port 10GBase LAN/WAN-XFP Flexible Card(HIC20)
					subbnameCR2D00EBGF10(675842),     --12-Port 100/1000Base-X-SFP Flexible Card(HIC20)
					subbnameCR2D00EBGE10(675843),     --12-Port 10/100/1000Base-RJ45 Flexible Card(HIC20)

					subbnameCR2D00EKGF10(675844) ,    --40-Port 100/1000Base-SFP Flexible Card(HIC20,Occupy two sub-slots)
					subbnameCR2D00EKGE10(675845) ,    --40-Port 10/100/1000Base-RJ45 Flexible Card(HIC20,Occupy two sub-slots)
					subbnameCR2D00L4XX10(675846),     --4-Port 10GBase WAN/LAN-XFP Flexible Card(HIC20,Occupy two sub-slots)
					subbnameCR2D00EMFE10(675847) ,    --48-Port 10/100Base Delander Flexible Card(HIC20)
					subbnameCR2D00P1XX10(675848) ,    --1-Port OC-192c/STM-64c POS-XFP Flexible Interface Card(Occupy two FIC slots)
					subbnameCR2D00E8GF10(675849) ,      --8 100/1000Base-X-SFP A(P10-A,1588v2)
					subbnameCR2D00A4CF10(675850) ,    --4-Port OC-3c/STM-1c ATM-SFP Flexible Interface Card(FIC)
					subbnameCR2D00P1UF10(675851) ,    --1-Port OC-48c/STM-16c POS-SFP Flexible Interface Card(FIC)
					subbnameCR2D00P2UF10(675852) ,    --2-Port OC-48c/STM-16c POS-SFP Flexible Interface Card(FIC)
					subbnameCR2D00P4HF10(675853) ,    --4-Port OC-12c/STM-4c POS-SFP Flexible Interface Card(FIC)
					subbnameCR2D00P4CF10(675854),     --4-Port OC-3c/STM-1c POS-SFP Flexible Interface Card(FIC)
					subbnameCR2D00P8CF10(675855) ,    --8-Port OC-3c/STM-1c POS-SFP Flexible Interface Card(FIC)
					subbnameCR2D00C2CF10(675856) ,    --2-Port Channelized OC-3c/STM-1c POS-SFP Flexible Interface Card(FIC)
					subbnameCR2D00CFE110(675857),     --24-Port Channelized E1/T1-DB100 Flexible Interface Card(FIC)
					subbnameCR2DL2XEEG10(675858),      --2-Port 10GBase LAN/WAN-XFP+20-Port 100/1000Base-X-SFP Flexible Card(HIC20,Occupy two sub-slots)
					-- FOr cx600 V8R5  NE20E
					subbnameCR2D00L2XF11(675870),       --2-Port 10GBase LAN/WAN-SFP+  Physical Interface Card
					subbnameCR2D00E8GF11(675871),       --8-Port 100/1000Base-X-SFP Physical Interface Card
					subbnameCR2D00E8GE11(675872),       --8-Port 10/100/1000Base-RJ45 Physical Interface Card
					subbnameCR2DL1XE8G10(675873),       -- CX68L1XE8GF, 1-Port 10GBase LAN/WAN-SFP+  8-Port 100/1000Base-X-SFP Physical Interface Card
					subbnameCR2D00C4CF11(675874),       --CX68C4CF    4-Port Channelized STM-1c POS-SFP  Physical Interface Card
					subbnameCR2D000IE110(675875),       --CX68MIE1    32-Port E1 Physical Interface Card(75ohm)
					subbnameCR2D000IE111(675876),       --CX68MIE1B   32-Port E1 Physical Interface Card(120ohm)
					subbnameCR2D000DE110(675877),       --CX68MDE1A   16-Port E1 Physical Interface Card(75ohm)
					subbnameCR2D000DE111(675878),       --CX68MDE1B   16-Port E1 Physical Interface Card(120ohm)
					subbnameCR2D00L4XF10(675879),       -- CX68L4XF, 4-Port 10GBase-X-SFP+High-speed Interface Card
					subbnameCR2D00P4CF11(675880),       -- CX67P4CFA, 4-Port OC-3c/STM-1c POS-SFP Flexible Interface Car

				--BEGIN: for NE20E V8R7 by j00289303
				subbnameCR2D00EAGF10(675882),		-- CX68EAGFD, 10-Port 100/1000Base-X-SFP Physical Interface Card
				subbnameCR2DL1XE8G11(675883),       	-- CX68L1XE8GFB, 1-Port 10GBase LAN/WAN-SFP+ + 8-Port 100/1000Base-X-SFP Physical Interface Card
				subbnameCR2DP4C2HF11(675884),	   	-- CX68P4CFC, 4-Port OC-3c/STM-1c (or 2-Port OC12c/STM-4c)  POS-SFP  Physical Interface Card
				subbnameCR2DP2C1HF11(675885),	   	-- CX68P2CFC, 2-Port OC-3c/STM-1c (or 1-Port OC12c/STM-4C) POS-SFP  Physical Interface Card
				subbnameCR2D0L2XFH10(675886),	   	-- CX68L2XFC, 2-Port 10GBase LAN/WAN-SFP+ Physical Interface Card H
				subbnameCR2D0EAGFH10(675887),	   	-- CX68EAGFD, 10-Port 100/1000Base-X-SFP Physical Interface Card H
				subbnameCR2D00E8GE12(675888),	   	-- CX68E8GED, 8-Port 100/1000Base-RJ45 Physical Interface Card
				subbnameCR2D00E1MF10(675889),	   	-- CX68E1MC,  1-Port 40GBase-CFP Physical Interface Card
				subbnameCR2D00L4XF11(675890),	   	-- CX68L4XFD, 4-Port 10GBase LAN/WAN-SFP+ Physical Interface Card
				subbnameCR2D00L2XF12(675891),	   	-- CX68L2XFC, 2-Port 10GBase LAN/WAN-SFP+ Physical Interface Card
				--END: for NE20E V8R7 by j00289303

-- CloudEngine: 0x000A8000~0x000A8fff(688128~692223)
					subbnameDE51DFCMA(688128),        --CloudEngine TOR CE6800 CE5800 FAN Control Card
					subbnameDE51DCTLA(688129),        --CloudEngine TOR CE6800 CE5800 Extend Interface Card
					subbnamePAC150WA(688130),         --CloudEngine TOR CE6800 CE5800 150W AC Power Module
					subbnamePAC350WA(688131),         --CloudEngine TOR CE6800 CE5800 350W AC Power Module,Front to Back
					subbnamePAC350WAB(688132),        --CloudEngine TOR CE6800 CE5800 350W AC Power Module,Back to Front
					subbnameFAN40SA(688133),          --CloudEngine TOR CE6800 CE5800 Fan box,Front to Back
					subbnameFAN40SAB(688134),         --CloudEngine TOR CE6800 CE5800 Fan box,Back to Front
					subbnameFAN40EA(688135),          --CloudEngine TOR CE6800 CE5800 Extend Fan box,Front to Back
					subbnameFAN40EAB(688136),          --CloudEngine TOR CE6800 CE5800 Extend Fan box,Back to Front

--Adapter Mount Card for iODN products: range: 0x000B0000~0x000BFFFF  720,896~786,431
					 subbnameAF11AMCX1(753921),                --AF11AMCX1
					 subbnameAF11AMCB1(753922),                --AF11AMCB1
					 subbnameAF11AMCC1(753923),                --AF11AMCC1
					 subbnameAF11AMCD1(753924),                --AF11AMCD1
					 subbnameAF11AMCX2(753925),                --AF11AMCX2
					 subbnameAF11AMCB2(753926),                --AF11AMCB2
					 subbnameAF11AMCC2(753927),                --AF11AMCC2
					 subbnameAF11AMCD2(753928),                --AF11AMCD2


--Security Product's TC-MIB value scope :       16711680 ~ 16777215  or Hex format:0x00ff0000 ~ 0x00ffffff  (Both 16711680 and 16777215 are included)

--USG2000/Eudemon200E
					 subbnameE180(16719885),             -- Wireless Data sub Card,E180,HSUPA/HSDPA/UMTS/EDGE/GPRS/GSM USB STICK,White,HUAWEI Standard
					 subbnameET128(16719886),                -- Wireless Data sub Card,ET128,HSDPA/TD-SCDMA/EDGE/GPRS/GSM USB STICK,HUAWEI Standard Version
					 subbnameEC169(16719887),                -- Wireless Data sub Card,EC169,CDMA2000 EV-DO Rev.A Rotatable USB Stick,White,Chinese Universal,RoHS



--Security Product's TC-MIB value scope :       16711680 ~ 16777215  or Hex format:0x00ff0000 ~ 0x00ffffff  (Both 16711680 and 16777215 are included)
--SVN Serie's TC-MIB vlaue scope:                   16740352 ~ 16744447  or Hex format:0x00ff7000~0x00ff7fff    (Both 16740352 and 16744447 are included)
--SVN
					 subbnameSVN3000CN1510(16740352),          -- High-rate encrypted board (CN1510)  SVN3000
		subbnameSVN5500CN1620(16740353),          -- SVN5500,SE41HSVA,High Speed SSL VPN Card,with HS General Security Platform Software,1*1

--Security Product's TC-MIB value scope :       16711680 ~ 16777215  or Hex format:0x00ff0000 ~ 0x00ffffff  (Both 16711680 and 16777215 are included)
--SIG9800 Serie's TC-MIB vlaue scope:                   16732160 ~ 16736255  or Hex format:0x00ff5000 ~ 0x00ff5fff  (Both 16732160 and 16736255 are included)
--SIG9800
					 subbnameSIG9800SPCA(16732160),                 --SPUA sub card
					 subbnameSIG9800BypassCard(16732161),           --Bypass sub card
		subbnameSUP34SFPCard(16732162),                --SUP,SUP34SFP,4-port GE Optical Interface Board(SFP),1*2
		subbnameSIG9800IG2D00E5XX00(16732163),         --SIG9800-X,IG21L5XXA0,5-Port 10GBase LAN/WAN-XFP Flexible Card A(P100-A,Supporting 1588v2,Occupy two sub-slots)
		subbnameSIG9800IG2D00P2XS00(16732164),         --SIG9800-X,IG21P2XXA0,2-Port OC-192c/STM-64c POS-XFP Flexible Card(P100,Occupy one sub-slot)
		subbnameSIG9800IG2D00P1MS00(16732165),         --SIG9800-X,IG21P1MZ0,1-Port OC-768c/STM-256c POS-2KM-LC Flexible Card(P100,Occupy two sub-slots)
		subbnameSIG9800IG2D00E4XF00(16732166),         --SIG9800-X,IG21E4XFA0,4-Port 10GBase LAN-SFP+ Flexible Card(P100,Occupy one sub-slots)
		subbnameSIG9800IG2D00EFGF01(16732167),         --SIG9800-X,IG21EFGFA0,24-Port 100/1000Base-X-SFP Flexible Card(P100,Occupy two sub-slots)
		subbnameSIG9800IG2D00EFGF02(16732168),         --SIG9800-X,IG21EFGFB1,24-Port 100/1000Base-X-SFP Flexible Card A(P101-A)
		subbnameSIG9800IG2D00E5XF00(16732169),         --SIG9800-X,IG21L5XFB1,5-Port 10GBase LAN/WAN-SFP+ Flexible Card A(P101-A)
		subbnameSIG9800IG2D00E1MS00(16732170),         --SIG9800-X,IG21E1MCB1,1-Port 40GBase LAN-CFP Flexible Card A(P101-A)
		subbnameSIG9800SUP5SPCA(16732171),             --SUP,SUP5SPCA,Service Processing Card,1*1
		subbnameSIG9800IG21L6XF0(16732172),            --SIG9800-X,IG21L6XF0,6-Port 10GBase LAN/WAN-SFP+ Flexible Card (P120)
		subbnameSIG9800IG21LBXF1(16732173),            --SIG9800-X,IG21LBXF1,12-Port 10GBase LAN/WAN-SFP+ Flexible Card (P240)
		subbnameSIG9800IG21E1NCB1(16732174),           --SIG9800-X,IG21E1NCB1,1-Port 100GBase-CFP Flexible Card (P240)

--Security Product's TC-MIB value scope :       16711680 ~ 16777215  or Hex format:0x00ff0000 ~ 0x00ffffff  (Both 16711680 and 16777215 are included)
--Eudemon8000E/USG9000 Serie's TC-MIB vlaue scope:  16748544 ~ 16752639  or Hex format:0x00ff9000 ~ 0x00ff9fff  (Both 16748544 and 16752639 are included)
--Eudemon8000E/USG9000 Board/Card :
					 subbnameEudemon8000ECR52E1XXT0(16748544), --CR52E1XX0,1*10GBase LAN-XFP Optical Interface LPU A
					 subbnameEudemon8000ECR52W1XXT0(16748545), --CR52W1XX0,1*10GBase WAN-XFP Optical Interface LPU A
					 subbnameEudemon8000ECR52P1XXT0(16748546), --CR52P1XX0,1*OC-192c/STM-64c POS-XFP Optical Interface LPU A
					 subbnameEudemon8000ECR52R1XF(16748547),   --CR52R1XX0,1*OC-192c/STM-64c RPR-XFP Optical Interface LPU A
					 subbnameEudemon8000ECR52E5GF(16748548),   --CR52E5GF,5-port GbE SFP Optical Interface LPU G
					 subbnameEudemon8000ECR52C8E10(16748549),  --CR52C8E10,8-Port Channelized E1-RJ45 Flexible Service Interface Card
					 subbnameEudemon8000ECR52C8T10(16748550),  --CR52C8T10,8-Port Channelized T1-RJ45 Flexible Service Interface Card
					 subbnameEudemon8000ECR52C1CF1(16748551),  --CR52C1CF1,1 port Channelized OC-3/STM-1 Flexible Service Interface Card
					 subbnameEudemon8000ECR52L1XX0(16748552),  --1-port 10GBase WAN/LAN XFP Flexible Interface Daughter Card
					 subbnameEudemon8000ECR52EBGF0(16748553),  --12-port 100/1000Base-X SFP Flexible Interface Daughter Card
					 subbnameEudemon8000ECR52EBGE0(16748554),  --12-port 10/100/1000Base-TX RJ45 Flexible Interface Daughter Card
					 subbnameEudemon8000ECR52P1XXBZ0(16748555),--1 port OC-192c/STM-64c POS-XFP Flexible Card
		subbnameEudemon8000ESU91L4XX00(16748556),	   --SU91L4XX00 4 Port 10G Base WAN/LAN-XFP
	  subbnameEudemon8000ESU91L4XX01(16748557),	   --SU91L4XX01 4 Port 10G Base LAN/LAN-XFP
	  subbnameEudemon8000ESU91SPCB02(16748558),	   --Eudemon8000E-X,SU91SPCB02,20G Firewall Performance Expansion Card(oversea),with HS General Security Platform Software
	  subbnameEudemon8000ESU91SPCC01(16748559),	   --Eudemon8000E-X,SU91SPCC01,40G Firewall Processing Card,with HS General Security Platform Software
	  subbnameEudemon8000ESU91SPCB01(16748560),	   --Eudemon8000E-X,SU91SPCB01,80G Firewall Processing card,with HS General Security Platform Software

-- USG9100 SubCard :
					 subbnameUSG9100SU61E8GF(16748564),      -- 8-port GE SubCard
					 subbnameUSG9100SU61P4UF(16748565),      -- 4-port 2.5G POS SubCard
					 subbnameUSG9100SU61E1XX(16748566),      -- 1-port 10G SubCard
					 subbnameUSG9100SU61W1XX(16748567),      -- 1-port 10G SubCard
					 subbnameUSG9100SU61P1XX(16748568),      -- 1-port 10G SubCard
					 subbnameUSG9100SU61X2G16(16748569),   -- 2-port 10G LAN SFP+ Optical Interface and 16-port GE Optical Interface Card(SFP) ,with HS General Security Platform Software
					 subbnameUSG9100E2XS(16748570),        -- 2*SFP+ Interface Broad,with HS General Security Platform Software
					 subbnameUSG9100E16GF(16748571),       -- 16*SFP Interface Board,with HS General Security Platform Software
					 subbnameEnd(2147483647)

					 }

		  HWPortType ::= TEXTUAL-CONVENTION
				STATUS current
				DESCRIPTION
					 "This data type is used as the syntax of the ifType
					 object in the (updated) definition of MIB-II's
					 ifTable.

					 The definition of this textual convention with the
					 addition of newly assigned values is published
					 periodically by the IANA, in either the Assigned
					 Numbers RFC, or some derivative of it specific to
					 Internet Network Management number assignments.  (The
					 latest arrangements can be obtained by contacting the
					 IANA.)

					 Requests for new values should be made to IANA via
					 email (iana@iana.org).

					 The relationship between the assignment of ifType
					 values and of OIDs to particular media-specific MIBs
					 is solely the purview of IANA and is subject to change
					 without notice.  Quite often, a media-specific MIB's
					 OID-subtree assignment within MIB-II's 'transmission'
					 subtree will be the same as its ifType value.
					 However, in some circumstances this will not be the
					 case, and implementors must not pre-assume any
					 specific relationship between ifType values and
					 transmission subtree OIDs.

					 "
				SYNTAX INTEGER
					 {
					 other(1),                       -- none of the following
					 regular1822(2),
					 hdh1822(3),
					 ddnX25(4),
					 rfc877x25(5),
					 ethernetCsmacd(6),
					 iso88023Csmacd(7),
					 iso88024TokenBus(8),
					 iso88025TokenRing(9),
					 iso88026Man(10),
					 starLan(11),
					 proteon10Mbit(12),
					 proteon80Mbit(13),
					 hyperchannel(14),
					 fddi(15),
					 lapb(16),
					 sdlc(17),
					 ds1(18),                        -- DS1-MIB
					 e1(19),                         -- Obsolete see DS1-MIB
					 basicISDN(20),
					 primaryISDN(21),
					 propPointToPointSerial(22),     -- proprietary serial
					 ppp(23),
					 softwareLoopback(24),
					 eon(25),                        -- CLNP over IP
					 ethernet3Mbit(26),
					 nsip(27),                       -- XNS over IP
					 slip(28),                       -- generic SLIP
					 ultra(29),                      -- ULTRA technologies
					 ds3(30),                        -- DS3-MIB
					 sip(31),                        -- SMDS, coffee
					 frameRelay(32),                 -- DTE only.
					 rs232(33),
					 para(34),                       -- parallel-port
					 arcnet(35),                     -- arcnet
					 arcnetPlus(36),                 -- arcnet plus
					 atm(37),                        -- ATM cells
					 miox25(38),
					 sonet(39),                      -- SONET or SDH
					 x25ple(40),
					 iso88022llc(41),
					 localTalk(42),
					 smdsDxi(43),
					 frameRelayService(44),          -- FRNETSERV-MIB
					 v35(45),
					 hssi(46),
					 hippi(47),
					 modem(48),                      -- Generic modem
					 aal5(49),                       -- AAL5 over ATM
					 sonetPath(50),
					 sonetVT(51),
					 smdsIcip(52),                   -- SMDS InterCarrier Interface
					 propVirtual(53),                -- proprietary virtual/internal
					 propMultiplexor(54),            -- proprietary multiplexing
					 ieee80212(55),                  -- 100BaseVG
					 fibreChannel(56),               -- Fibre Channel
					 hippiInterface(57),             -- HIPPI interfaces
					 frameRelayInterconnect(58),     -- Obsolete use either [frameRelay(32)] or [frameRelayService(44)].
					 aflane8023(59),                 -- ATM Emulated LAN for 802.3
					 aflane8025(60),                 -- ATM Emulated LAN for 802.5
					 cctEmul(61),                    -- ATM Emulated circuit
					 fastEther(62),                  -- Fast Ethernet (100BaseT)
					 isdn(63),                       -- ISDN and X.25
					 v11(64),                        -- CCITT V.11/X.21
					 v36(65),                        -- CCITT V.36
					 g703at64k(66),                  -- CCITT G703 at 64Kbps
					 g703at2mb(67),                  -- Obsolete see DS1-MIB
					 qllc(68),                       -- SNA QLLC
					 fastEtherFX(69),                -- Fast Ethernet (100BaseFX)
					 channel(70),                    -- channel
					 ieee80211(71),                  -- radio spread spectrum
					 ibm370parChan(72),              -- IBM System 360/370 OEMI Channel
					 escon(73),                      -- IBM Enterprise Systems Connection
					 dlsw(74),                       -- Data Link Switching
					 isdns(75),                      -- ISDN S/T interface
					 isdnu(76),                      -- ISDN U interface
					 lapd(77),                       -- Link Access Protocol D
					 ipSwitch(78),                   -- IP Switching Objects
					 rsrb(79),                       -- Remote Source Route Bridging
					 atmLogical(80),                 -- ATM Logical Port
					 ds0(81),                        -- Digital Signal Level 0
					 ds0Bundle(82),                  -- group of ds0s on the same ds1
					 bsc(83),                        -- Bisynchronous Protocol
					 async(84),                      -- Asynchronous Protocol
					 cnr(85),                        -- Combat Net Radio
					 iso88025Dtr(86),                -- ISO 802.5r DTR
					 eplrs(87),                      -- Ext Pos Loc Report Sys
					 arap(88),                       -- Appletalk Remote Access Protocol
					 propCnls(89),                   -- Proprietary Connectionless Protocol
					 hostPad(90),                    -- CCITT-ITU X.29 PAD Protocol
					 termPad(91),                    -- CCITT-ITU X.3 PAD Facility
					 frameRelayMPI(92),              -- Multiproto Interconnect over FR
					 x213(93),                       -- CCITT-ITU X213
					 adsl(94),                       -- Asymmetric Digital Subscriber Loop
					 radsl(95),                      -- Rate-Adapt. Digital Subscriber Loop
					 sdsl(96),                       -- Symmetric Digital Subscriber Loop
					 vdsl(97),                       -- Very H-Speed Digital Subscrib. Loop
					 iso88025CRFPInt(98),            -- ISO 802.5 CRFP
					 myrinet(99),                    -- Myricom Myrinet
					 voiceEM(100),                   -- voice recEive and transMit
					 voiceFXO(101),                  -- voice Foreign Exchange Office
					 voiceFXS(102),                  -- voice Foreign Exchange Station
					 voiceEncap(103),                -- voice encapsulation
					 voiceOverIp(104),               -- voice over IP encapsulation
					 atmDxi(105),                    -- ATM DXI
					 atmFuni(106),                   -- ATM FUNI
					 atmIma (107),                   -- ATM IMA
					 pppMultilinkBundle(108),        -- PPP Multilink Bundle
					 ipOverCdlc (109),               -- IBM ipOverCdlc
					 ipOverClaw (110),               -- IBM Common Link Access to Workstn
					 stackToStack (111),             -- IBM stackToStack
					 virtualIpAddress (112),         -- IBM VIPA
					 mpc (113),                      -- IBM multi-protocol channel support
					 ipOverAtm (114),                -- IBM ipOverAtm
					 iso88025Fiber (115),            -- ISO 802.5j Fiber Token Ring
					 tdlc (116),                     -- IBM twinaxial data link control
					 gigabitEthernet (117),          -- Gigabit Ethernet
					 hdlc (118),                     -- HDLC
					 lapf (119),                     -- LAP F
					 v37 (120),                      -- V.37
					 x25mlp (121),                   -- Multi-Link Protocol
					 x25huntGroup (122),             -- X25 Hunt Group
					 trasnpHdlc (123),               -- Transp HDLC
					 interleave (124),               -- Interleave channel
					 fast (125),                     -- Fast channel
					 ip (126),                       -- IP (for APPN HPR in IP networks)
					 docsCableMaclayer (127),        -- CATV Mac Layer
					 docsCableDownstream (128),      -- CATV Downstream interface
					 docsCableUpstream (129),        -- CATV Upstream interface
					 a12MppSwitch (130),             -- Avalon Parallel Processor
					 tunnel (131),                   -- Encapsulation interface
					 coffee (132),                   -- coffee pot
					 ces (133),                      -- Circuit Emulation Service
					 atmSubInterface (134),          -- ATM Sub Interface
					 l2vlan (135),                   -- Layer 2 Virtual LAN using 802.1Q
					 l3ipvlan (136),                 -- Layer 3 Virtual LAN using IP
					 l3ipxvlan (137),                -- Layer 3 Virtual LAN using IPX
					 digitalPowerline (138),         -- IP over Power Lines
					 mediaMailOverIp (139),          -- Multimedia Mail over IP
					 dtm (140),                      -- Dynamic syncronous Transfer Mode
					 dcn (141),                      -- Data Communications Network
					 ipForward (142),                -- IP Forwarding Interface
					 msdsl (143),                    -- Multi-rate Symmetric DSL
					 ieee1394 (144),                 -- IEEE1394 High Performance Serial Bus
					 if-gsn (145),                   -- HIPPI-6400
					 dvbRccMacLayer (146),           -- DVB-RCC MAC Layer
					 dvbRccDownstream (147),         -- DVB-RCC Downstream Channel
					 dvbRccUpstream (148),           -- DVB-RCC Upstream Channel
					 atmVirtual (149),               -- ATM Virtual Interface
					 mplsTunnel (150),               -- MPLS Tunnel Virtual Interface
					 srp (151),                      -- Spatial Reuse Protocol
					 voiceOverAtm (152),             -- Voice Over ATM
					 voiceOverFrameRelay (153),      -- Voice Over Frame Relay
					 idsl (154),                     -- Digital Subscriber Loop over ISDN
					 compositeLink (155),            -- Avici Composite Link Interface
					 ss7SigLink (156),               -- SS7 Signaling Link
					 propWirelessP2P (157),          -- Prop. P2P wireless interface
					 frForward (158),                -- Frame Forward Interface
					 rfc1483 (159),                  -- Multiprotocol over ATM AAL5
					 usb (160),                      -- USB Interface
					 ieee8023adLag (161),            -- IEEE 802.3ad Link Aggregate
					 bgppolicyaccounting (162),      -- BGP Policy Accounting
					 frf16MfrBundle (163),           -- FRF .16 Multilink Frame Relay
					 h323Gatekeeper (164),           -- H323 Gatekeeper
					 h323Proxy (165),                -- H323 Voice and Video Proxy
					 mpls (166),                     -- MPLS
					 mfSigLink (167),                -- Multi-frequency signaling link
					 hdsl2 (168),                    -- High Bit-Rate DSL - 2nd generation
					 shdsl (169),                    -- Multirate HDSL2
					 ds1FDL (170),                   -- Facility Data Link 4Kbps on a DS1
					 pos (171),                      -- Packet over SONET/SDH Interface
					 dvbAsiIn (172),                 -- DVB-ASI Input
					 dvbAsiOut (173),                -- DVB-ASI Output
					 plc (174),                      -- Power Line Communtications
					 nfas (175),                     -- Non Facility Associated Signaling
					 tr008 (176),                    -- TR008
					 gr303RDT (177),                 -- Remote Digital Terminal
					 gr303IDT (178),                 -- Integrated Digital Terminal
					 isup (179),                     -- ISUP
					 propDocsWirelessMaclayer (180), -- prop/Maclayer
					 propDocsWirelessDownstream (181),   -- prop/Downstream
					 propDocsWirelessUpstream (182), -- prop/Upstream
					 hiperlan2 (183),                -- HIPERLAN Type 2 Radio Interface
					 propBWAp2Mp (184),              -- PropBroadbandWirelessAccesspt2multipt
					 sonetOverheadChannel (185),     -- SONET Overhead Channel
					 digitalWrapperOverheadChannel (186),    -- Digital Wrapper
					 aal2 (187),                     -- ATM adaptation layer 2
					 radioMAC (188),                 -- MAC layer over radio links
					 atmRadio (189),                 -- ATM over radio links
					 imt (190),                      -- Inter Machine Trunks
					 mvl (191),                      -- Multiple Virtual Lines DSL
					 reachDSL (192),                 -- Long Reach DSL
					 frDlciEndPt (193),              -- Frame Relay DLCI End Point
					 atmVciEndPt (194),              -- ATM VCI End Point
					 opticalChannel (195),           -- Optical Channel
					 opticalTransport (196),         -- Optical Transport
					 propAtm (197),                  -- Proprietary ATM
					 voiceOverCable (198),           -- Voice Over Cable Interface
					 infiniband (199),               -- Infiniband
					 teLink (200),                   -- TE Link
					 q2931 (201),                    -- Q.2931
					 virtualTg (202),                -- Virtual Trunk Group
					 sipTg (203),                    -- SIP Trunk Group
					 sipSig (204),                   -- SIP Signaling
					 docsCableUpstreamChannel (205), -- CATV Upstream Channel
					 econet (206),                   -- Acorn Econet
					 pon155 (207),                   -- FSAN 155Mb Symetrical PON interface
					 pon622 (208),                   -- FSAN622Mb Symetrical PON interface
					 bridge (209),                   -- Transparent bridge interface
					 linegroup (210),                -- Interface common to multiple lines
					 voiceEMFGD (211),               -- voice E&M Feature Group D
					 voiceFGDEANA (212),             -- voice FGD Exchange Access North American
					 voiceDID (213),                 -- voice Direct Inward Dialing
					 mpegTransport (214),            -- MPEG transport interface
					 sixToFour (215),                -- 6to4 interface
					 gtp (216),                      -- GTP (GPRS Tunneling Protocol)
					 pdnEtherLoop1 (217),            -- Paradyne EtherLoop 1
					 pdnEtherLoop2 (218),            -- Paradyne EtherLoop 2
					 opticalChannelGroup (219),      -- Optical Channel Group
					 homepna (220),                  -- HomePNA ITU-T G.989
					 gfp (221),                      -- Generic Framing Procedure (GFP)
					 ciscoISLvlan (222),             -- Layer 2 Virtual LAN using Cisco ISL
					 fcipLink (224),                 -- FCIP Link
					 rpr (225),                      -- Resilient Packet Ring Interface Type
					 qam (226),                      -- RF Qam Interface
					 lmp (227),                      -- Link Management Protocol
					 cblVectaStar (228),             -- Cambridge Broadband Limited VectaStar
					 docsCableMCmtsDownstream (229), -- CATV Modular CMTS Downstream Interface
					 adsl2 (230),                    -- Asymmetric Digital Subscriber Loop Version 2
					 macSecControlledIF (231),       -- MACSecControlled
					 macSecUncontrolledIF (232),     -- MACSecUncontrolled

-- huawei expanding
					 aponOltPort(501),               -- Apon olt port
					 aponOltSubport(502),            -- Apon olt sub port
					 aponOntPort(503),               -- Apon ont port
					 atmPort(504),                   -- atm port
					 atmSubport(505),                -- atm sub port
					 adslPort(506),                  -- Already defined in RFC
					 lanPort(507),                   -- lan port
					 cescPort(508),                  -- E1 port of CESC board
					 cesdPort(509),                  -- V35 port of CESD board
					 frcPort(510),                   -- E1 port FR board
					 fpcSubport(511),                -- fpc sub port
					 sepPort(512),                   -- sep port
					 vpringPort(513),                -- STM-4 VPRING port
					 eimPort(514),                   -- FE port of BAS board
					 geimPort(515),                  -- GE port of BAS board
					 basMainport(516),               -- ATM port of BAS board used to create connection
					 apruCes(517),                   -- Apon CES port
					 apruLan(518),                   -- Apon LAN port
					 asxSoftSar(519),                -- soft sar port of ASX board
					 asxHardSar(520),                -- hard sar port of ASX board
					 cesE1Port(521),                 -- E1 port of CES board, for TDM use
					 e1Port(522),                    -- E1 port of CES
					 t1Port(523),                    -- T1 port of CES
					 pstnPort(524),                  -- pstn port
					 braPort(525),                   -- pstn port
					 praPort(536),                   -- bra port
					 cdiPort(539),                   -- vfb port
					 vfbPort(540),                   -- pstn port
					 atiPort(541),                   -- ati port
					 mlcE1Port(542),                 -- mlcE1 port
					 v5TkPort(543),                  -- v5Tk port
					 comPort(544),                   -- com port
					 v35Port(545),                   -- v35 port
					 mmxIwe8Port(546),               -- CES port on MMXC board
					 frPortE1(547),                  -- E1 port of FR board
					 frPortT1(548),                  -- T1 port of FR board
					 frPortV35(549),                 -- V35 port of FR board
					 aiuAtmPort(550),                -- ATM port on AIU board
					 imaPort(551),                   -- IMA port
					 e3Port(552),                    -- E3 port
					 mmxImaPort(554),                -- IMA port on MMX board
					 nullPort(555),                  -- null port
					 shdslPort(556),                 -- G.SHDSL  port
					 iadMainport(557),               -- iad main port
					 iadPort(558),                   -- ida port
					 cesSDTVPort(559),               -- CES SDT virtual port
					 vlanVPort(560),                 -- VLAN virtual port of LAN board
					 frVCCIndexVPort(561),           -- FR VCC virtual port
					 frStreamVPort(562),             -- FR stream virtual port
					 imaGroupVPort(563),             -- IMA group virtual port
					 adslInterleaveVPort(564),       -- Interleavet virtual port of ADSL board
					 adslFastVPort(565),             -- Fast virtual port of ADSL board
					 lanTrunkVPort(566),             -- Trunk virtual port of LAN board
					 sepsmxAtmPort(568),             -- Used to configure the SEPL or SMXL port feature
					 dehaUdtPort(569),               -- UDT Port of DEHA board
					 t1TdmPort(570),                -- T1 port of TDM
					 cposT1ccPort(571),             -- CPOS port of T1CC
					 lanswitchPort(572),             -- port of the board for lanswitch between chassises
					 vsrPort(573),                   -- VSR port of OFCA board or SFEA
					 sfpClusterPort(574),            -- SFP port of the board for lanswitch between chassises
-- OFA5920
					 bitsPort(575),                  -- BITS port
					 gponOnuPort(576),               -- GPON upstream port
					 eponOnuPort(577),               -- EPON upstream port
					 hwPort(578),                    -- HW port of PVM
		  gponOltPor(579),                -- GPON OLT port
-- MA5200
					 debugserial(580),               -- debug serial port
					 debugnet(581),                  -- debug net port
-- MA5600
					 nativeTDME1Port(589),           -- Native TDM E1 port
					 nativeTDMT1Port(590),           -- Native TDM T1 port
					 tengeOptPort(591),              -- 10GE optical port
					 eponOltPort(592),               -- EPON OLT port
					 stm-1Port(593),                 -- STM-1 port of H801O2CE subboard
-- MA5200
					 sdlFE1Port(600),                -- SDL FE1 port
					 sdlShdslPort(601),              -- SDL G.SHDSL port
-- MA5635
					 adslPstnPort(700),                -- adsl como port, especially for adsl como board
					 vdslPstnPort(701),                -- vdsl como port, especially for vdsl como board
-- SD5103
					 serialSrvPort(799),               -- serial service port
					 autoAdptPort(800),                -- auto adpt port
					 catvPort(801),                    -- CATV port

-- SRG
					 fxoport(802),                    -- FXO port
-- MA5631
					 eocport(803),                    -- EoC master RF port
-- MA5633
					 docsisport(804),                 -- docsis port of board HS33CDAA,the board has only one port(docsisPort).
-- MA5616
					 veiPort(805),                    -- Vei port of board NLV.
-- MA5694S
					vdslNNIPort(806),                 -- VDSL upstream port.
-- 8010
					 dsp(65536),                      -- dsp port
					 bits(65537),                     -- bits port
					 clk(65538),                      -- clk port
					 mon(65539),                      -- mon port
					 aux(65540),                      -- aux port
					 sdho(65541),                     -- sdho port
					 sdhe(65542),                     -- sdhe port

-- hwRPS
					fanPort(786932),                   --Fan module fan port
					dcoutputPort(786933),              --Up converter module DC output port
					dcinputPort(786694),               --Down converter module DC input port
-- MA5200 add definition of port type 0x21000(135168) ~ 0x21FFF(139263)
					 portnameH521ATMOC3S(135168),
					 portnameH521ATMOC3M(135169),
					 portnameH521ATMOC12S(135170),
					 portnameH521ATMOC12M(135171),
					 portnameH521CPOSOC3S(135172),
					 portnameH521CPOSOC3M(135173),
					 portnameH521CPOSOC48S(135174),
					 portnameH521CPOSOC48M(135175),
					 portnameH521FEE(135176),
					 portnameH521FEOSSFP(135177),
					 portnameH521FEOMSFP(135178),
					 portnameH521GEESFP(135179),
					 portnameH521GEOSSFP(135180),
					 portnameH521GEOMSFP(135181),
					 portnameH521POSOC3S(135182),
					 portnameH521POSOC3M(135183),
					 portnameH521POSOC12S(135184),
					 portnameH521POSOC12M(135185),
					 portnameH521POSOC48S(135186),
					 portnameH521POSOC48M(135187),
					 portnameH521E1(135188),
					 portnameH521T1(135189),
					 portnameH521E3(135190),
					 portnameH521T3(135191),
					 portnameH521CE1(135192),
					 portnameH521CT1(135193),
					 portnameH521CPOSOC3(135194),
					 portnameH521GEEGBIC(135195),
					 portnameH521GEOMGBIC(135196),
					 portnameH521GEOSGBIC(135197),
					 portnameH521GEOMMTRJ(135198),
					 portnameH521GEOSMTRJ(135199),
					 portnameH521GEOSLC(135200),
					 portnameH521GEOMLC(135201),
					 portnameH521GEOSSC(135202),
					 portnameH521GEOMSC(135203),
					 portnameH521FEOSMTRJ(135204),
					 portnameH521FEOMMTRJ(135205),
					 portnameH521FEOSSC(135206),
					 portnameH521FEOMSC(135207),
					 portnameH521FEOSLC(135208),
					 portnameH521FEOMLC(135209),
					 portnameH522GERPR(135210),
					 portnameH523POS10G(135211),
					 portnameH523GE10GLAN(135212),
					 portnameH523GE10GWAN(135213),
					 portnameH521ATMOC3(135214),
					 portnameH521ATMOC12(135215),
					 portnameH521CPOSOC48S2(135216),
					 portnameH521FEOSFP(135217),
					 portnameH521POSOC3(135218),
					 portnameH521POSOC12(135219),
					 portnameH521POSOC48(135220),
					 portnameH521GEOGBIC(135221),
					 portnameH521GEOLC(135222),
					 portnameH521GEOSC(135223),
					 portnameH521GEOSFP(135224),
					 portnameH521FEOLC(135225),
					 portnameH521FEOSC(135226),
					 portnameH523POS10GS(135227),
					 portnameH523POS10GM(135228),
					 portnameH523GE10GLANS(135229),
					 portnameH523GE10GLANM(135230),
					 portnameH523GE10GWANS(135231),
					 portnameH523GE10GWANM(135232),
					 portnameH521SMUFE(135233),
					 portnameH523SMUGGE(135234),
-- WA5700:
					 bwaTdmPort(155648),               -- TDM port of the BWA

-- 8031:        S23&33&53&CX200D porttype definition

					 portnameS233353SFP(536576),    -- The port when SFP transceiver plugged in
					 portnameS233353ESFP(536577),   -- The port when ESFP transceiver plugged in
					 portnameS233353RJ45(536578),   -- The port with RJ45 type
					 portnameS233353FIBER(536579),  -- The port with fiber type without transceiver
					 portnameS233353COMBOFIBER(536580),  -- The port with combo fiber type
					 portnameS233353COMBOCOPPER(536581), -- The port with combo copper type

-- S9300:       0x000A1000~0x000A1fff(659456~663551)
					 portnameLE01SFP(659456),
					 portnameLE01ESFP(659457),
					 portnameLE01RJ45(659458),
					 portnameLE01ERJ45(659459),
					 portnameLE01RJ45POE(659460),
					 portnameLE01XFP(659461),
					 portnameLE01EXFP(659462),
					 portnameLE01COMBO(659463),
					 portnameLE02EPON(659464),
					 portnameLE02VXFP(659465),
					 portnameLE02POS(659466),

-- AR:          0x000A3000~0x000A3fff(667648~671743)
					 portnameAR01FELANRJ45(667648),          -- The port with RJ45 type of FE LAN
					 portnameAR01FELANFIBER(667649),         -- The port with fiber type of FE LAN
					 portnameAR01FEWANRJ45(667650),          -- The port with RJ45 type of FE WAN
					 portnameAR01FEWANFIBER(667651),         -- The port with fiber type of FE WAN
					 portnameAR01GELANRJ45(667652),          -- The port with RJ45 type of GE LAN
					 portnameAR01GELANFIBER(667653),         -- The port with fiber type of GE LAN
					 portnameAR01GEWANRJ45(667654),          -- The port with RJ45 type of GE WAN
					 portnameAR01GEWANFIBER(667655),         -- The port with fiber type of GE WAN
					 portnameAR01COMBOFIBER(667656),         -- The port with combo fiber type
					 portnameAR01COMBOCOPPER(667657),        -- The port with combo copper type
					 portnameAR01E1DB9(667658),              -- The port with E1/CE1 type DB9 head
					 portnameAR01T1DB9(667659),              -- The port with T1/CT1 type DB9 head
					 portnameAR01SYNSERIAL(667660),          -- The port with Sync Serial type
					 portnameAR01ASYNSERIAL(667661),         -- The port with Async Serial type
					 portnameAR01ISDNVOICE(667662),          -- The port with ISDN voice type
					 portnameAR01FXS(667663),                -- The port with FXS type
					 portnameAR01FXO(667664),                -- The port with FXO type
					 portnameAR01ADSL(667665),               -- The port with ADSL type
					 portnameAR01VDSL(667666),               -- The port with VDSL type
					 portnameGSGDSL(667667),                 -- The port with G.SHDSL type with Ethernet mode
					 portnameAR01EPON(667668),               -- The port with EPON type
					 portnameAR01GPON(667669),               -- The port with GPON type
					 portnameAR013G(667670),                 -- The port with 3G type
					 portnameAR01ISDNDATA(667671),           -- The port with ISDN data type
					 portnameAR01E1FDB9(667672),             -- The port with E1-F type DB9 head
					 portnameAR01T1FDB9(667673),             -- The port with T1-F type DB9 head
					 portnameGSGDSLATM(667674),              -- The port with G.SHDSL type with ATM mode
					 portnameCPOS(667675),                   -- The port with CPOS type
					 portnameAR01E1RJ45(667676),             -- The port with E1/CE1 type RJ45 head
					 portnameAR01T1RJ45(667677),             -- The port with T1/CT1 type RJ45 head
					 portnameAR01E1FRJ45(667678),            -- The port with E1-F type RJ45 head
					 portnameAR01T1FRJ45(667679),            -- The port with T1-F type RJ45 head
					 portnameAR01EM(667680),                 -- The port with E&M type

-- CloudEngine:    0x000A8000~0x000A8fff(688128~692223)
					 portnameDCDE01SFP(688128),              -- The port with 10/100/1000BASE-T type
					 portnameDCDE01QSFP(688129),             -- The port with 10G BASE-T type
					 portnameDCDE01XFP(688130),              -- The port with 10G SFP type
					 portnameDCDE01QXFP(688131),             -- The port with 40G SFP type
					 portnameDCDE01VXFP(688132),             -- The port with 40G/4*10G SFP type
					 portnameDCDE01RJ45(688133),             -- The port with RJ45 type
					 portnameDCDE01CFP(688134),              -- The port with 100G SFP type
					 portnameDCDE01CFP2(688135),             -- The port with 100G Split SFP type
					 portnameDCDE01SFP2(688137)  ,            -- The port with GE SFP type
-- USG2200,USG2100
					 wifi(16711680),                   -- WIFI card communicates with WIFI terminals as a wireless AP, and supports IEEE 802.11b/ 802.11g
					 veport(16711681),                 -- The Virtual Ethernet (VE) is applied to the PPPoEoA and IPoEoA.
																  -- It functions on the interface board. Externally it features Ethernet attributes
					 g3Port(16711682),                 -- 3G supports three wireless communication mode, including both WCDMA/CDMA2000/TD-SCDMA and corresponding 2G mode.
					 serialPort(16711683),             -- The serial port is used for the exchange of information between computers or devices
																  -- one bit at a time over a single channel. Serial communications can be synchronous or asynchronous.
																  -- Both sender and receiver must use the same baud rate, parity, and control information.
					 dialerPort(16711684),             -- The dialer interface is used as dialing interface of pppoe client ,supports pppoe protocol
					 t1(16711685),
					 electricityPort(16711686)         --electricity port
					 }

		  HWUnSupportNodeInteger ::= TEXTUAL-CONVENTION
				STATUS current
				DESCRIPTION
					 "
					 This object is not used any longer.To the nodes that don't supported in the MIB table ,the default value
					 should be return for keeping the integrity of the OID in the MIB table ,
					 and the type of the default value is INTEGER, and default value is 65535.

					 "
				SYNTAX INTEGER { defaultValue(65535) }

		  HWUnSupportNodeString ::= TEXTUAL-CONVENTION
				STATUS current
				DESCRIPTION
					 "
					 This object is not used any longer.To the nodes that don't supported in the MIB table ,the default value
					 should be return for keeping the integrity of the OID in the MIB table,
					 and the default string is the null string. "
				SYNTAX OCTET STRING (SIZE (0))

		  HWUnSupportNodeIPAddress ::= TEXTUAL-CONVENTION
				STATUS current
				DESCRIPTION
					 "This object is not used any longer.To the nodes that don't supported in the MIB table ,the default value
					 should be return for keeping the integrity of the OID in the MIB table,
					 and the default IP address is 0.0.0.0."
				SYNTAX IpAddress

		  HWUnSupportNodeMacAddress ::= TEXTUAL-CONVENTION
				STATUS current
				DESCRIPTION
					 "This object is not used any longer.To the nodes that don't supported in the MIB table ,the default value
					 should be return for keeping the integrity of the OID in the MIB table,
					 and the default string is '000000'. "

				SYNTAX MacAddress
		  HWVirtualEntityType ::= TEXTUAL-CONVENTION
				STATUS current
				DESCRIPTION
					 "This object is not used any longer.To show the relevant virtual entity type in vender type object.
					 "
				SYNTAX INTEGER
					 {
					 other(1),                       -- none of the following

	  -- from 536577 to 561150 is for 8031 Whole BOARD
 -- 8031:
					 -- from 536577 to 536999 is for 8031 MPU Whole board
					 virentCX61DEVCR52SRUA(536577),   -- the old whole board of SRUA saled before V3R7 version in CX600(whithout SBOM information)
					 virentCX61DEVCR52MPUA(536578),   -- the old whole board of MPUA saled before V3R7 version in CX600(whithout SBOM information)
					 virentCX61DEVCR52MPUB(536579),   -- the old whole board of MPUB saled before V3R7 version in CX600(whithout SBOM information)
					 virentCX61DEVCR55MPUD(536580),   -- the old whole board of CR55MPUD saled before V3R7 version in CX600(whithout SBOM information)
					 virentCX61DEVCR52MPUD(536581),   -- the old whole board of CR52MPUD saled before V3R7 version in CX600(whithout SBOM information)
					 virentCX61DEVCR52SRUC(536582),   -- the old whole board of SRUC saled before V3R7 version in CX600(whithout SBOM information)
					 virentCX61DEVCR52MPUC(536583),   -- the old whole board of MPUC saled before V3R7 version in CX600(whithout SBOM information)

					 virentCX61DEVCX6D0SRUA410(536584), -- V6R1 for CX6D0SRUA410(SBOM),Switch and Route Processing Unit A4(Including 1*2G Memory and 1*1G CF Card)
					 virentCX61DEVCX6D0MPUB410(536585), -- V6R1 for CX6D0MPUB410(SBOM),Main Processing Unit B4(Including 1*2G Memory and 1*1G CF Card)
					 virentCX67DEVCX67MPUG(536586),     -- V6R2 for CX67MPUG,Main Processing Unit G
					 virentCX61DEVCR57MPUH(536587),     -- the new whole board of CR57MPUH V6R5 version in CX600(whithout SBOM information)
					 virent8090DEVCX6D00MPUK10(536588), -- V8R5 for SBOM, CX6D00MPUK10, Main Processing Unit K  ,in -country


					 -- from 537000 to 537799 is for 8031 SFU Whole board
					 virentCX61DEVCR52SFUA(537000),       -- the old whole board of SFUA saled before V3R7 version in CX600(whithout SBOM information)
					 virentCX61DEVCR52SFUC(537001),       -- the old whole board of SFUC saled before V3R7 version in CX600(whithout SBOM information)
					 virentCX61DEVCR52SFUD(537002),       -- the old whole board of SFUD saled before V3R7 version in CX600(whithout SBOM information)
					 virentCX61DEVCR52SFUF(537003),       -- the old whole board of SFUF saled before V3R7 version in CX600(whithout SBOM information)
					 virentCX61DEVCR52SFUG(537004),       -- the old whole board of SFUG saled before V3R7 version in CX600(whithout SBOM information)
					 virentCX61DEVCR52SFUI(537005),       -- the old whole board of SFUI saled before V3R7 version in CX600(whithout SBOM information)
					 virentCX61DEVCR52SFEA(537006),       -- the old whole board of SFEA saled before V3R7 version in CX600(whithout SBOM information)
					 virentCX61DEVCR52SFEB(537007),       -- the old whole board of SFEB saled before V3R7 version in CX600(whithout SBOM information)
					 virentCX61DEVCR57SFU40A(537008),     -- the old whole board of SFU40A saled before V3R7 version in CX600(whithout SBOM information)
					 virentCX61DEVCR57SFU40B(537009),     -- the old whole board of SFU40B saled before V3R7 version in CX600(whithout SBOM information)

					 virentCX61DEVCX6DSFUI401B(537010),    -- V6R1 for CX6DSFUI401B(SBOM), 40Gbps Switch Fabric Unit B
					 virentCX61DEVCX6DSFUI401C(537011),    -- V6R1 for CX6DSFUI401C(SBOM), 40Gbps Switch Fabric Unit C
					 virentCX61DEVCX61SFUG40GBPS(537012),  -- V6R1 for CX61-SFUG-40Gbps(SBOM), Switch Fabric Unit G

					 virentCX61DEVCR57SFU100C(537013),     -- Two piece 8890, X8 100G SFU
					 virentCX61DEVCR57SFU200B(537014),     -- Two piece 5802, X16 100G-200G SFU
					 virentCX61DEVCR57SFU200C(537015),     -- Two piece 5802, X8 100G-200G SFU

					 virentCX61DEVCR57SRU100A(537016),     -- Two piece 8890, 100G SFU, used with X8 SRUA100A MPU
					 virentCX61DEVCR57SRU200A(537017),     -- Two piece 5802, 200G SFU, used with X8 SRUA200A MPU

					 virentCX61DEVCR57LPUF41A(537018),     -- LPUF41A 40G LPU,SD58X2 Solution ,MIPS CPU
					 virentCX61DEVCR57LPUF101A(537019),    -- Double LPUF41A, 100G LPU

					 -- from 537800 to 540671 is for 8031 LPU Whole board and other board
					 virentCX67DEVCX67NPUI20A(537800),    -- V6R2 for CX67NPUI20A, Flexible Card Line Processing Unit
					 virent8090DEVCX6D0NSU5010(537801),   -- V8R5 for SBOM ,CX6D0NSU5010, Network Switch Unit (NSU-50)  in -country
					 virent8090DEVCX6D00L2XF10(537802),      -- CX6D00L2XF10, 2-Port 10GBase LAN/WAN-SFP+ Service Interface Card(SIC)
					 virent8090DEVCX6D00E8GF10(537803),   -- CX6D00E8GF10, 8-Port 100/1000Base-X-SFP Service Interface Card(SIC)
					 virent8090DEVCX6D00E8GE10(537804),   -- CX6D00E8GE10, 8-Port 10/100/1000Base-RJ45 Service Interface Card(SIC)

					 virent8090DEVCX6X0PWRDC70(537805),   -- V8R5 for SBOM ,  CX600-X2 DC/DC Power Module
					 virent8090DEVCX6M001FBX71(537806),   -- V8R5 for SBOM ,  CX600-X1 FAN Module
					 virent8090DEVCX6M002FBX72(537807),   -- V8R5 for SBOM ,  CX600-X2 FAN Module

					 virent8090DEVCX6B0BKP0271(537808),   -- V8R5 for SBOM ,  CX600-X2 BACK Plane
					 virent8090DEVCX6B0BKP0171(537809),
					 virent8090DEVCX6D000IE170(537810),   -- V8R5 for SBOM ,  32E1 interface card, 75 ohm

					 virent8090DEVCX6D000IE171(537811),   -- V8R5 for SBOM ,  32E1 interface card,120 ohm

					 virent8090DEVCX6D00P4CF70(537812),   -- V8R5 for SBOM ,  4*155M CPOS interface card

					 virent8090DEVCX6DNSU12010(537813),   -- V8R5 for SBOM ,CX6D0NSU12010, Network Switch Unit (NSU-120)  in -country
					 virent8090DEVCX6D000DE110(537814),   -- V8R5 for SBOM ,  16E1 interface card, 75 ohm
					 virent8090DEVCX6D000DE111(537815),   -- V8R5 for SBOM ,  16E1 interface card, 120 ohm

					 virentCX67DEVCX6D000FBX70(540670),    -- V6R2 for ****, CX600-X1/X2 Fan Unit
					 virentCX67DEVCX6D00PSUD70(540671),    -- V6R2 for CX6D00PSUD70, CX600-X1/X2 DC Power Supply Unit
					 -- from 538000 to 538010
					 virentCX62DEVCX67MPUG0(538000),       -- for CX600-DO Main Processing Unit G (Including 1*1G CF Card)
					 virentCX62DEVCX67NPUI20(538001),      -- for CX600-DO Integrated Network Processing Unit with 2-Port 10GBase LAN/WAN-XFP(NPUI-20)
					 virentCX62DEVCX67NPU20B0(538002),     -- for CX600-DO Integrated Network Processing Unit(NPUI-20-B)
					 virentCX62DEVCR52MPUB4(538003),       -- for CX600-DO Main Processing Unit B4(Including 1*2G Memory and 1*1G CF Card)
					 virentCX62DEVCR52SFU40B0(538004),     -- for CX600-DO 40Gbps Switch Fabric Unit B
					 virentCX62DEVCR52SRU40A4(538005),     -- for CX600-DO Switch and Route Processing Unit A4(Including 1*2G Memory and 1*1G CF Card)
					 virentCX62DEVCR52SFU40C0(538006),     -- for CX600-DO 40Gbps Switch Fabric Unit C
					 virentCX62DEVCR52MPUD0(538007),       -- for CX600-DO Main Processing Unit D(Including 1*2G Memory and 1*1G CF Card)
					 virentCX62DEVCR52ISUF10(538008),      -- for CX600-DO Flexible Card Integrated Service Unit(ISUF-10,four sub-slots)
					 virentCX62DEVCR52ISUF20(538009),      -- for CX600-DO Flexible Card Integrated Service Unit(ISUF-20,two sub-slots)
					 virentCX62DEVCR52ISUF40(538010),      -- for CX600-DO Flexible Card Integrated Service Unit(ISUF-40,two sub-slots)
					 virent8090DEVCX6D0L4XXA10(538011),    -- for CX600-DO, CX6D0L4XXA10,4-Port 10GBase LAN/WAN-XFP Integrated Line Processing Unit (ISUI-41,Supporting 1588v2)
					 virent8090DEVCX6D0EKGFA10(538012),    -- for CX600-DO, CX6D0EKGFA10,40-Port 100/1000Base-X-SFP Integrated Line Processing Unit (ISUI-41,Supporting 1588v2)
					 virent8090DEVCX6DL2XEEG1A(538013),    -- for CX600-DO, CX6DL2XEEG1A,2-Port 10GBase LAN/WAN-XFP+20-Port 100/1000Base-X-SFP Integrated Line Processing Unit (ISUI-41,Supporting 1588v2)
					 virent8090DEVCX6DISUF5010(538014),    -- Flexible Card Integrated Service Unit(ISUF-50,4 sub-slots)
					 virent8090DEVCX6D00L4XX10(538015),    -- for V600R005C00 CX600, CX6D00L4XX10,4-Port 10GBase LAN/WAN-XFP Integrated Integrated Service Unit (ISUI-41)
					 virent8090DEVCX6D00EMGF10(538016),    -- for V600R005C00 CX600, CX6D00EMGF10,48-Port 100/1000Base-X-SFP Integrated Integrated Service Unit (ISUI-41)
					 virent8090DEVCX6DL2XEFG10(538017),    -- for V600R005C00 CX600, CX6DL2XEFG10,2-Port 10GBase LAN/WAN-XFP+24-Port 100/1000Base-X-SFP Integrated Integrated Service Unit (ISUI-41)
					 virentCX62DEVCR57MPUH(538018),        -- for CX600-DO Main Processing Unit H(Including 2G Memory )
					 virentCX61DEVCR57SFU100D(538019),     -- one piece 5802, X8 100G SFU
					 virentCX61DEVCR57SRU100D(538020),     -- one piece 5802, 100G SFU, used with X8 SRUA100A MPU
					 virent8090DEVCX6D00MPUK70(538021),    --V8R5 for SBOM,   CX6D00MPUK70, Main Processing Unit K , overseas
	 -- from 561152 to 159743 is for 8090 Whole BOARD
 -- 8090:
					 virent8090DEVLPU(561152),        -- The whole IO board, include all entities on the slot
					 virent8090DEVMPU(561153),        -- Whole MPU Board, include all entities on the slot, virtual entity
					 virent8090DEVSRU(561154),        -- Whole SRU Board, include all entities on the slot, virtual entity
					 virent8090DEVSFU(561155),        -- Switch Fabric Unit for Full Capacity System, include all entities on the slot,virtual entity
					 virent8090DEVSRUSFU(561156),     -- Switch Fabric Unit for Half & Halflow Frame System, include all entities on the slot,virtual entity
					 virent8090DEVICU(561157),        -- Whole ICU Board, include all entities on the slot, virtual entity
					 virent8090DEVECU(561158),        -- Whole ECU Board, include all entities on the slot, virtual entity


					 -- from 561159 to 561999 is for 8090 MPU Whole board
					 virent8090DEVCR52SRUA(561159),   -- the old whole board of SRUA saled before V3R7 version in 8090(whithout SBOM information)
					 virent8090DEVCR52MPUA(561160),   -- the old whole board of MPUA saled before V3R7 version in 8090(whithout SBOM information)
					 virent8090DEVCR52MPUB(561161),   -- the old whole board of MPUB saled before V3R7 version in 8090(whithout SBOM information)
					 virent8090DEVCR55MPUD(561162),   -- the old whole board of CR55MPUD saled before V3R7 version in 8090(whithout SBOM information)
					 virent8090DEVCR52MPUD(561163),   -- the old whole board of CR52MPUD saled before V3R7 version in 8090(whithout SBOM information)
					 virent8090DEVCR52SRUC(561164),   -- the old whole board of SRUC saled before V3R7 version in 8090(whithout SBOM information)
					 virent8090DEVCR52MPUC(561165),   -- the old whole board of MPUC saled before V3R7 version in 8090(whithout SBOM information)

					 virent8090DEVCR5D0SRUA470(561166),   -- V6R1 for CR5D0SRUA470(SBOM), Switch and Route Processing Unit A4(Including 1*2G Memory and 1*1G CF Card)
					 virent8090DEVCR5D0MPUB460(561167),   -- V6R1 for CR5D0MPUB460(SBOM), Main Processing Unit B4(Including 1*2G Memory and 1*1G CF Card)
					 virent8090DEVCR5D00MPUG70(561168),   -- V6R2 for CR5D00MPUG70(SBOM), Main Processing Unit G0(Including 1*1G CF Card)

					 virent8090DEVCR57SRU100A(561169),     -- Two piece 8890, 100G SFU, used with X8 SRUA100A MPU
					 virent8090DEVCR57SRU200A(561170),     -- Two piece 5802, 200G SFU, used with X8 SRUA200A MPU

					 virent8090DEVCR57MPUH(561171),        -- the new whole board of MPUH for V6R5 version in 8090(whithout SBOM information)
					 virent8090DEVCR57SRU100D(561172),     -- One piece 5802, 100G SFU, used with X8 SRUA100A MPU
					 virent8090DEVCR5D00MPUK70(561173),    -- V8R5 for SBOM,   CR5D00MPUK70, Main Processing Unit K, NE40E
				virent8090DEVCR5D0MPUB570(561174),    -- V8R6C10 for CR5D0MPUB570(SBOM), Main Processing Unit B5

					 -- from 562000 to 562999 is for 8090 SFU Whole board
					 virent8090DEVCR52SFUA(562000),       -- the old whole board of SFUA saled before V3R7 version in 8090(whithout SBOM information)
					 virent8090DEVCR52SFUC(562001),       -- the old whole board of SFUC saled before V3R7 version in 8090(whithout SBOM information)
					 virent8090DEVCR52SFUD(562002),       -- the old whole board of SFUD saled before V3R7 version in 8090(whithout SBOM information)
					 virent8090DEVCR52SFUF(562003),       -- the old whole board of SFUF saled before V3R7 version in 8090(whithout SBOM information)
					 virent8090DEVCR52SFUG(562004),       -- the old whole board of SFUG saled before V3R7 version in 8090(whithout SBOM information)
					 virent8090DEVCR52SFUI(562005),       -- the old whole board of SFUI saled before V3R7 version in 8090(whithout SBOM information)
					 virent8090DEVCR52K-SFEA(562006),     -- V8R5 for CR52K-SFEA(SBOM), Switch Fabric Extended Unit A
					 virent8090DEVCR52SFEB(562007),       -- the old whole board of SFEB saled before V3R7 version in 8090(whithout SBOM information)
					 virent8090DEVCR57SFU40A(562008),     -- the old whole board of SFU40A saled before V3R7 version in 8090(whithout SBOM information)
					 virent8090DEVCR57SFU40B(562009),     -- the old whole board of SFU40B saled before V3R7 version in 8090(whithout SBOM information)

					 virent8090DEVCR5DSFUI407B(562010),     -- V6R1 for CR5DSFUI407B(SBOM), 40Gbps Switch Fabric Unit B
					 virent8090DEVCR5DSFUI407C(562011),     -- V6R1 for CR5DSFUI407C(SBOM), 40Gbps Switch Fabric Unit C
					 virent8090DEVCR5DSFUG40GBPS(562012),   -- V6R1 for CR52-SFUG-40Gbps(SBOM), Switch Fabric Unit G

					 virent8090DEVCR57SFU100C(562013),     -- Two piece 8890, X8 100G SFU
					 virent8090DEVCR57SFU200B(562014),     -- Two piece 5802, X16 100G-200G SFU
					 virent8090DEVCR57SFU200C(562015),     -- Two piece 5802, X8 100G-200G SFU
					 virent8090DEVCR57SFU100D(562016),     -- One piece 5802, X8 100G SFU
					 virent8090DEVCR5DSFUFA06C(562017),    -- V8R5 for CR5DSFUFA06C(SBOM), 100G Switch Fabric Unit B(SFUF-100-C)
					 virent8090DEVCR5DSFUIK06A(562018),    -- V8R5 for CR5DSFUIK06A(SBOM), 400G Switch Fabric Unit A for Single Chassis(SFUI-400-A)
					 virent8090DEVCR55C-ECUA(562019),      -- V8R5 for CR55C-ECUA(SBOM), Cluster Electric Cross Unit A

					 virent8090DEVCR5DSFU0K06B(562021),    -- V8R5 for CR5DSFU0K06B(SBOM), NE5000E-X16 400G CLC Switch Fabric Unit B for Single Chassis (SFU-400-B)
					 -- from 563000 to 564499 is for 8090 LPU Whole board
					 virent8090DEVLPUA(563000),       -- the old whole board of LPUA saled before V3R7 version in 8090(whithout SBOM information)
					 virent8090DEVLPUB(563001),       -- the old whole board of LPUB saled before V3R7 version in 8090(whithout SBOM information)
					 virent8090DEVLPUC(563002),       -- the old whole board of LPUC saled before V3R7 version in 8090(whithout SBOM information)
					 virent8090DEVLPUE(563003),       -- the old whole board of LPUE saled before V3R7 version in 8090(whithout SBOM information)
					 virent8090DEVLPUG(563004),       -- the old whole board of LPUG saled before V3R7 version in 8090(whithout SBOM information)
					 virent8090DEVLPUH(563005),       -- the old whole board of LPUH saled before V3R7 version in 8090(whithout SBOM information)
					 virent8090DEVLPUI(563006),       -- the old whole board of LPUI saled before V3R7 version in 8090(whithout SBOM information)
					 virent8090DEVLPUM(563007),       -- the old whole board of LPUM saled before V3R7 version in 8090(whithout SBOM information)
					 virent8090DEVLPUF10(563008),     -- the old whole board of LPUF10 saled before V3R7 version in 8090(whithout SBOM information)
					 virent8090DEVLPUK0(563009),     -- the old whole board of LPUK0(03030GQU) saled before V3R7 version in 8090(whithout SBOM information)
					 virent8090DEVLPUK1(563010),     -- the old whole board of LPUK1(03030HPS) saled before V3R7 version in 8090(whithout SBOM information)
					 virent8090DEVLPUK2(563011),     -- the old whole board of LPUK2(03030HVN) saled before V3R7 version in 8090(whithout SBOM information)
					 virent8090DEVLPUK3(563012),     -- the old whole board of LPUK3(03030HYQ) saled before V3R7 version in 8090(whithout SBOM information)
					 virent8090DEVLPUKD0(563013),     -- the old whole board of LPUKD0(03030KJY) saled before V3R7 version in 8090(whithout SBOM information)
					 virent8090DEVLPUKD1(563014),     -- the old whole board of LPUKD1(03030KKB) saled before V3R7 version in 8090(whithout SBOM information)
					 virent8090DEVLPUK21(563015),     -- the old whole board of LPUK21(03030KKU) saled before V3R7 version in 8090(whithout SBOM information)
					 virent8090DEVLPUK31(563016),     -- the old whole board of LPUK31(03030KKV) saled before V3R7 version in 8090(whithout SBOM information)
					 virent8090DEVLPUF40(563017),     -- the old whole board of LPUF40 saled before V3R7 version in 8090(whithout SBOM information)
					 virent8090DEVTSUA(563018),       -- the old whole board of TSUA saled before V3R7 version in 8090(whithout SBOM information)
					 virent8090DEVTSUG(563019),       -- the old whole board of TSUG saled before V3R7 version in 8090(whithout SBOM information)
					 virent8090DEVTSUF10(563020),     -- the old whole board of TSUF10 saled before V3R7 version in 8090(whithout SBOM information)
					 virent8090DEVLPUKB(563021),      -- the old whole board of LPUKB saled before V3R7 version in 8090(whithout SBOM information)
					 virent8090DEVSPUF10(563022),     -- the old whole board of SPUF10 saled before V3R7 version in 8090(whithout SBOM information)
					 virent8090DEVRNRSPU(563023),     -- the old whole board of RNRSPU saled before V3R7 version in 8090(whithout SBOM information)
					 virent8090DEVRNRLPUB(563024),    -- the old whole board of RNRLPUB saled before V3R7 version in 8090(whithout SBOM information)
					 virent8090DEVRNRLPUD(563025),    -- the old whole board of RNRLPUD saled before V3R7 version in 8090(whithout SBOM information)
					 virent8090DEVRNRLPUF(563026),    -- the old whole board of RNRLPUF saled before V3R7 version in 8090(whithout SBOM information)

					 virent8090DEVCR5MLPUF402A(563027),    -- V6R1 for CR5MLPUF402A(SBOM),Flexible Card Line Processing Unit(LPUF-40,2 sub-slots) A (L3VPN, MVPN, IPv6 Enhanced)
					 virent8090DEVCR5MLPUF402B(563028),    -- V6R1 for CR5MLPUF402B(SBOM),Flexible Card Line Processing Unit(LPUF-40,2 sub-slots) B
					 virent8090DEVCR5MVSUF1010(563029),     -- V6R2 for CR5MVSUF1010(SBOM),Flexible Card Versatile Service Unit 10(VSUF-10) (WP21ESPUd board)
					 virent8090DEVCR5MVSUI201A(563030),     -- V6R2 for CR5MVSUI201A(SBOM),Integrated Versatile Service Unit 20 A(VSUI-20-A)
					 virent8090DEVCR5DNPUI2070(563031),     -- V6R2 for CR5DNPUI2070(SBOM),Network Processing Unit Integrated with 2-Port 10GBase LAN/WAN-XFP(NPUI-20-A)

					 virent8090DEVCR57LPUF41A(563032),     -- LPUF41A 40G LPU,SD58X2 Solution ,MIPS CPU
					 virent8090DEVCR57LPUF101A(563033),    -- Double LPUF41A, 100G LPU
					 --for V6R3 LPUF41A & LPUF101A packing boards 2011-01-15
					 virent8090DEVCR57L8XXB0(563034),      -- LPUI-41,8*10GBase LAN/WAN-XFP(CR57LPUF41A+2*CR57L4XX)
					 virent8090DEVCR57L4XXB0(563035),      -- LPUI-41,4*10GBase LAN/WAN-XFP(CR57LPUF41A+2*CR52L2XXN)
					 virent8090DEVCR57EMGFB0(563036),      -- LPUI-41,48*FE/GE-SFP(CR57LPUF41A+2*CR57EFGF)
					 virent8090DEVCR57L2XEFGB0(563037),    -- LPUI-41,2*10GBase LAN/WAN-XFP-24*FE/GE-SFP(CR57LPUF41A+CR52L2XXN+CR57EFGF)
					 virent8090DEVCR57L4XXC0(563038),      -- LPUI-41,4*10GBase LAN/WAN-XFP-1588V2(CR57LPUF41A+2*CR52L2XXNB)
					 virent8090DEVCR57EKGFC0(563039),      -- LPUI-41,40*FE/GE-SFP-1588V2(CR57LPUF41A+2*CR57EEGFB)
					 virent8090DEVCR57L2XEEGC0(563040),    -- LPUI-41,2*10GBase LAN/WAN-XFP-20*FE/GE-SFP-1588V2(CR57LPUF41A+CR52L2XXNB+CR57EEGFB)
					 virent8090DEVCR57L8XXB1(563041),      -- LPUS-41,8*10GBase LAN/WAN-XFP(CR57LPUF41A+2*CR57L4XX)
					 virent8090DEVCR57L4XXB1(563042),      -- LPUS-41,4*10GBase LAN/WAN-XFP(CR57LPUF41A+2*CR52L2XXN)
					 virent8090DEVCR57EMGFB1(563043),      -- LPUS-41,48*FE/GE-SFP(CR57LPUF41A+2*CR57EFGF)
					 virent8090DEVCR57LAXXB0(563044),      -- LPUI-100,10*10GBase LAN/WAN-XFP-1588V2(CR57LPUF101A+2*CR56L5XX)
					 virent8090DEVCR57EDXFB0(563045),      -- LPUI-100,16*10GBase LAN-SFP+(CR57LPUF101A+4*CR56E4XF)

					 --end for V6R3 LPUF41A & LPUF101A packing boards 2011-01-15
					 virent8090DEVCR52LPUF21E(563046),   -- V6R3C05 for CR52LPUF21E(SBOM),Flexible Card Line Processing Unit(LPUF-21,2 sub-slots) E
					 virent8090DEVCR52LPUF40E(563047),   -- V6R3C05 for CR52LPUF40E(SBOM),Flexible Card Line Processing Unit(LPUF-40,2 sub-slots) E
					 virent8090DEVCR57LAXXB1(563048),   -- V6R3C05 for CR57LAXXB1(SBOM),10-Port 10GBase LAN/WAN-XFP Line Processing Unit S(LPUS-100)
					 virent8090DEVCR57EDXFB1(563049),   -- V6R3C05 for CR57EDXFB1(SBOM),16-Port 10GBase LAN-SFP+ Line Processing Unit S(LPUS-100)
					 virent8090DEVCR57E1NCA1(563050),   -- V6R3C05 for CR57EDXFB1(SBOM),16-Port 10GBase LAN-SFP+ Line Processing Unit S(LPUS-100)
					 virent8090DEVCR57L2XEFGB1(563051),   -- V6R3C05 for CR57L2XEFGB1(SBOM),2-Port 10GBase LAN/WAN-XFP+24-Port 100/1000Base-X-SFP Line Processing Unit S(LPUS-41)
					 virent8090DEVCR5DVSUI201A(563052),   -- V6R3C05 for CR5DVSUI201A(SBOM),Integrated Versatile Service Unit 20 A(VSUI-20-A)
					 virent8090DEVCR53LPUF50(563053),      -- LPUF50 40G LPU,SD5880 Solution ,MIPS CPU
					 virent8090DEVCR5DLPUF5070(563054),    -- Flexible Card Line Processing Unit(LPUF-50,4 sub-slots)

					 virent8090DEVCR5D00EKGE20(563055),    -- V6R1 for CR5D00EKGE20(SBOM), 40-Port 10/100/1000Base-RJ45 Switch Line Processing Unit(LPUS-20), V600R001 zhi hou an cheng pin ban bao zhuang, xu yao zai xin de ti xi shang bao zhuang yi ci
					 virent8090DEVCR5D00EKGF21(563056),    -- V6R1 for CR5D00EKGF21(SBOM), 40-Port 100/1000Base-X-SFP Switch Line Processing Unit(LPUS-20), V600R001 zhi hou an cheng pin ban bao zhuang, xu yao zai xin de ti xi shang bao zhuang yi ci
					 virent8090DEVCR5D00L4XX21(563057),    -- V6R1 for CR5D00L4XX21(SBOM), 4-Port 10GBase LAN/WAN-XFP Switch Line Processing Unit(LPUS-20), V600R001 zhi hou an cheng pin ban bao zhuang, xu yao zai xin de ti xi shang bao zhuang yi ci
					 virent8090DEVCR5D00L4XX20(563058),    -- V6R1 for CR5D00L4XX20(SBOM), 4-Port 10GBase LAN/WAN-XFP Integrated Line Processing Unit (LPUI-40), V600R001 zhi hou an cheng pin ban bao zhuang, xu yao zai xin de ti xi shang bao zhuang yi ci
					 virent8090DEVCR5D00EKGF20(563059),    -- V6R1 for CR5D00EKGF20(SBOM), 40-Port 100/1000Base-X-SFP Integrated Line Processing Unit(LPUI-40), V600R001 zhi hou an cheng pin ban bao zhuang, xu yao zai xin de ti xi shang bao zhuang yi ci

					 --for V6R5C00 LPU packing boards 2011-09-23
					 virent8090DEVCR57LPUF101E0(563100),   -- V6R5C00 for CR57LPUF101E0(SBOM),Flexible Card Line Processing Unit(LPUF-100,4 sub-slots) E

					 --for V6R5C00 & JICAI packing boards 2011-12-27
					 virent8090DEVCX6DSFUIA07B(563103),    -- V6R5C00 for CX6DSFUIA07B(SBOM),100Gbps Switch Fabric Unit B(SFUI-100-B)
					 virent8090DEVCX6D0SRUA611(563104),    -- V6R5C00 for CX6D0SRUA611(SBOM),Switch and Route Processing Unit A6(Including 1*2G Memory and 1*1G CF Card)
					 virent8090DEVCX6DSFUIA07C(563105),    -- V6R5C00 for CX6DSFUIA07C(SBOM),100Gbps Switch Fabric Unit C(SFUI-100-C)
					 virent8090DEVCX6DISUF401B(563106),    -- V6R5C00 for CX6DISUF401B(SBOM),Flexible Card Integrated Service Unit(ISUF-40-B,two sub-slots)
					 virent8090DEVCX6D0L4XXA1B(563107),    -- V6R5C00 for CX6D0L4XXA1B(SBOM),4-Port 10GBase LAN/WAN-XFP Integrated Integrated Service Unit (ISUI-41-B,Supporting 1588v2)
					 virent8090DEVCX6D0EKGFA1B(563108),    -- V6R5C00 for CX6D0EKGFA1B(SBOM),40-Port 100/1000Base-X-SFP Integrated Integrated Service Unit (ISUI-41-B,Supporting 1588v2)
					 virent8090DEVCX6DL2XEEG1B(563109),    -- V6R5C00 for CX6DL2XEEG1B(SBOM),2-Port 10GBase LAN/WAN-XFP+20-Port 100/1000Base-X-SFP Integrated Integrated Service Unit (ISUI-41-B,Supporting 1588v2)
					 virent8090DEVCX6D00EMGF1B(563110),    -- V6R5C00 for CX6D00EMGF1B(SBOM),48-Port 100/1000Base-X-SFP Integrated Integrated Service Unit (ISUI-41-B)
					 virent8090DEVCX6DL2XEFG1B(563111),    -- V6R5C00 for CX6DL2XEFG1B(SBOM),2-Port 10GBase LAN/WAN-XFP+24-Port 100/1000Base-X-SFP Integrated Integrated Service Unit (ISUI-41-B)
					 virent8090DEVCX6DISUFA010(563112),    -- V6R5C00 for CX6DISUFA010(SBOM),Flexible Card Line Processing Unit(ISUF-100,4 sub-slots)
					 virent8090DEVCX6D0LAXXA10(563113),    -- V6R5C00 for CX6D0LAXXA10(SBOM),10-Port 10GBase LAN/WAN-XFP Integrated Integrated Service Unit (ISUI-100,Supporting 1588v2)
					 virent8090DEVCX6D00L4XX1B(563114),    -- V6R5C00 for CX6D00L4XX1B(SBOM),4-Port 10GBase LAN/WAN-XFP Integrated Integrated Service Unit (ISUI-41-B)

					 virent8090DEVCR5DNPU50E70(563115),    -- V8R5 for SBOM ,CR5DNPU50E70, Network Processing Unit(NPU-50-E) in -country
					 virent8090DEVCR5D0NPU5070(563116),    -- V8R5 for SBOM ,CR5D0NPU5070, Network Processing Unit (NPU-50), NE40E
					 virent8090DEVCR5DNPU12070(563117),    -- V8R5 for SBOM ,CR5D0NPU12070, Network Processing Unit (NPU-120), NE40E
					 virent8090DEVCR5DNPU1207E(563118),    -- V8R5 for SBOM ,CR5D0NPU1207E, Network Processing Unit (NPU-120-E), NE40E

					 -- from 564500 to 159743 is for 8090 OTHER board
					 virent8090DEVFCARD(564500),          -- the old whole board of Flex-card saled before V3R7 version in 8090(whithout SBOM information)
					 virent8090DEVCR5M000CMU60(564501),   -- V6R1 for CR5M000CMU60(SBOM), Centralized Monitor Unit(CMU)
					 virent8090DEVCR5M000FBX60(564502),   -- V6R1 for CR5M000FBX60(SBOM), Fan Box
					 virent8090DEVCR5M000PEM60(564503),   -- V6R1 for CR5M000PEM60(SBOM), Power Filter Unit(PFU)
					 -- V8R5 CX600 X1/X2   NE40E
					 virent8090DEVCR5D00L2XF70(564519),   -- CR5D00L2XF70, 2-Port 10GBase LAN/WAN-SFP+  Physical Interface Card(PIC)
					 virent8090DEVCR5D00E8GF71(564520),   -- CR5D00E8GF71, 8-Port 100/1000Base-X-SFP  Physical Interface Card(PIC)
					 virent8090DEVCR5D00E8GE70(564521),   -- CR5D00E8GE70,  8-Port 10/100/1000Base-RJ45 Physical Interface Card(PIC)

					 -- from 564610 to 564660 is for V6R6C00 LPU packing boards 2012-03-23
					 -- for NE40E
					 virent8090DEV0305CR5DLPUF5070(564610),   -- V6R6C00 for CR5DLPUF5070(SBOM),Flexible Card Line Processing Unit(LPUF-50,four slots)
					 virent8090DEVCR5DLPUF5170(564611),   -- V6R6C00 for CR5DLPUF5170(SBOM),Flexible Card Line Processing Unit(LPUF-51,2 sub-slots)
					 virent8090DEVCR5DLPUF517B(564612),   -- V6R6C00 for CR5DLPUF517B(SBOM),Flexible Card Line Processing Unit(LPUF-51,2 sub-slots) B
					 virent8090DEVCR5D0L5XFA71(564614),   -- V6R6C00 for CR5D0L5XFA71(SBOM),5-Port 10GBase LAN/WAN-SFP+ Integrated Line Processing Unit (LPUI-51)
					 virent8090DEVCR5D0L5XFA7B(564615),   -- V6R6C00 for CR5D0L5XFA7B(SBOM),5-Port 10GBase LAN/WAN-SFP+ Integrated Line Processing Unit B(LPUI-51-B)
					 virent8090DEVCR5D00L5XF72(564616),   -- V6R6C00 for CR5D00L5XF72(SBOM),5-Port 10GBase LAN/WAN-SFP+ Line Processing Unit S(LPUS-51)
					 virent8090DEVCR5D0L4XFA70(564617),   -- V6R6C00 for CR5D0L4XFA70(SBOM),4-Port 10GBase LAN/WAN-SFP+ Integrated Line Processing Unit (LPUI-51)
					 virent8090DEVCR5D0L4XFA7B(564618),   -- V6R6C00 for CR5D0L4XFA7B(SBOM),4-Port 10GBase LAN/WAN-SFP+ Integrated Line Processing Unit B(LPUI-51-B)
					 virent8090DEVCR5D00L4XF71(564619),   -- V6R6C00 for CR5D00L4XF71(SBOM),4-Port 10GBase LAN/WAN-SFP+ Line Processing Unit S(LPUS-51)
					 virent8090DEVCR5D0EMGFA70(564620),   -- V6R6C00 for CR5D0EMGFA70(SBOM),48-Port 100/1000Base-X-SFP Integrated Line Processing Unit (LPUI-51)
					 virent8090DEVCR5D0EMGFA7B(564621),   -- V6R6C00 for CR5D0EMGFA7B(SBOM),48-Port 100/1000Base-X-SFP Integrated Line Processing Unit B(LPUI-51-B)
					 virent8090DEVCR5D00EMGF73(564622),   -- V6R6C00 for CR5D00EMGF73(SBOM),48-Port 100/1000Base-X-SFP Line Processing Unit S(LPUS-51)
					 virent8090DEVCR5DL2XEFG7A(564623),   -- V6R6C00 for CR5DL2XEFG7A(SBOM),2-Port 10GBase LAN/WAN-SFP+ + 24-Port 100/1000Base-X-SFP Integrated Line Processing Unit (LPUI-51)
					 virent8090DEVCR5DL2XEFG7B(564624),   -- V6R6C00 for CR5DL2XEFG7B(SBOM),2-Port 10GBase LAN/WAN-SFP+ + 24-Port 100/1000Base-X-SFP Integrated Line Processing Unit B(LPUI-51-B)
					 virent8090DEVCR5DL2XEFG72(564625),   -- V6R6C00 for CR5DL2XEFG72(SBOM),2-Port 10GBase LAN/WAN-SFP+ + 24-Port 100/1000Base-X-SFP Line Processing Unit S(LPUS-51)
					 virent8090DEVCR5D0L5XFA7L(564626),   -- V6R6C00 for CR5D0L5XFA7L(SBOM),5-Port 10GBase LAN/WAN-SFP+ Integrated Line Processing Unit L(LPUI-51-L)
					 virent8090DEVCR5DL2XEIG7L(564627),   -- V6R6C00 for CR5DL2XEIG7L(SBOM),2-Port 10GBase LAN/WAN-SFP+ + 32-Port 100/1000Base-X-SFP Integrated Line Processing Unit L(LPUI-51-L)
					 virent8090DEVCR5D0EMGFA7L(564628),   -- V6R6C00 for CR5D0EMGFA7L(SBOM),48-Port 100/1000Base-X-SFP Integrated Line Processing Unit L(LPUI-51-L)
					 virent8090DEVCR5D0EFGFA73(564629),   -- V6R6C00 for CR5D0EFGFA73(SBOM),24-Port 100/1000Base-X-SFP Integrated Line Processing Unit L(LPUI-21-L)
					 virent8090DEVCR5DL1XEDG70(564630),   -- V6R6C00 for CR5DL1XEDG70(SBOM),1-Port 10GBase LAN/WAN-SFP+ + 16-Port 100/1000Base-X-SFP Integrated Line Processing Unit L(LPUI-21-L)
					 virent8090DEVCR5DLPUFA071(564632),   -- V6R6C00 for CR5DLPUFA071(SBOM),Flexible Card Line Processing Unit(LPUF-101,4 sub-slots)
					 virent8090DEVCR5DLPUFA07B(564633),   -- V6R6C00 for CR5DLPUFA07B(SBOM),Flexible Card Line Processing Unit(LPUF-101,4 sub-slots) B
					 virent8090DEVCR5D00E2MC70(564635),   -- V6R6C00 for CR5D00E2MC70(SBOM),2-Port 40GBase LAN-CFP Integrated Line Processing Unit (LPUI-101)
					 virent8090DEVCR5D00E2MC7B(564636),   -- V6R6C00 for CR5D00E2MC7B(SBOM),2-Port 40GBase LAN-CFP Integrated Line Processing Unit B(LPUI-101-B)
					 virent8090DEVCR5D00E2MC71(564637),   -- V6R6C00 for CR5D00E2MC71(SBOM),2-Port 40GBase LAN-CFP Line Processing Unit S(LPUS-101)
					 virent8090DEVCR5D0LAXFA71(564638),   -- V6R6C00 for CR5D0LAXFA71(SBOM),10-Port 10GBase LAN/WAN-SFP+ Integrated Line Processing Unit (LPUI-101)
					 virent8090DEVCR5D0LAXFA7B(564639),   -- V6R6C00 for CR5D0LAXFA7B(SBOM),10-Port 10GBase LAN/WAN-SFP+ Integrated Line Processing Unit B(LPUI-101-B)
					 virent8090DEVCR5D0LAXFA72(564640),   -- V6R6C00 for CR5D0LAXFA72(SBOM),10-Port 10GBase LAN/WAN-SFP+ Integrated Line Processing Unit (LPUI-101)
					 virent8090DEVCR5D00E1NC72(564641),   -- V6R6C00 for CR5D00E1NC72(SBOM),1-Port 100GBase-CFP Integrated Line Processing Unit (LPUI-101)
					 virent8090DEVCR5D00E1NC73(564642),   -- V6R6C00 for CR5D00E1NC73(SBOM),1-Port 100GBase-CFP Line Processing Unit S(LPUS-101)

					 -- for CX600 local
					 virent8090DEVLOCALCX6DISUF5010(564643),   -- V6R6C00 for CX6DISUF5010(SBOM),Flexible Card Integrated Service Unit(ISUF-50,four sub-slots)
					 virent8090DEVCX6DISUF5110(564644),   -- V6R6C00 for CX6DISUF5110(SBOM),Flexible Card Integrated Service Unit(ISUF-51,two sub-slots)
					 virent8090DEVCX6DISUF511B(564645),   -- V6R6C00 for CX6DISUF511B(SBOM),Flexible Card Integrated Service Unit(ISUF-51-B,two sub-slots)
					 virent8090DEVCX6D0L5XFA11(564646),   -- V6R6C00 for CX6D0L5XFA11(SBOM),5-Port 10GBase LAN/WAN-SFP+ Integrated Integrated Service Unit (ISUI-51,Supporting 1588v2,4 port 10GE is enabled by default)
					 virent8090DEVCX6D0L5XFA1B(564647),   -- V6R6C00 for CX6D0L5XFA1B(SBOM),5-Port 10GBase LAN/WAN-SFP+ Integrated Integrated Service Unit B(ISUI-51-B,Supporting 1588v2,4 port 10GE is enabled by default)
					 virent8090DEVCX6DL4XEBG1A(564648),   -- V6R6C00 for CX6DL4XEBG1A(SBOM),4-Port 10GBase LAN/WAN-SFP++12-Port 100/1000Base-X-SFP Integrated Integrated Service Unit (ISUI-51,Supporting 1588v2)
					 virent8090DEVCX6DL4XEBG1B(564649),   -- V6R6C00 for CX6DL4XEBG1B(SBOM),4-Port 10GBase LAN/WAN-SFP++12-Port 100/1000Base-X-SFP Integrated Integrated Service Unit B(ISUI-51-B,Supporting 1588v2)
					 virent8090DEVCX6DL2XEIG1A(564650),   -- V6R6C00 for CX6DL2XEIG1A(SBOM),2-Port 10GBase LAN/WAN-SFP++32-Port 100/1000Base-X-SFP Integrated Integrated Service Unit (ISUI-51,Supporting 1588v2,2 port 10GE + 20 port FE/GE are enabled by default)
					 virent8090DEVCX6DL2XEIG1B(564651),   -- V6R6C00 for CX6DL2XEIG1B(SBOM),2-Port 10GBase LAN/WAN-SFP++32-Port 100/1000Base-X-SFP Integrated Integrated Service Unit B(ISUI-51-B,Supporting 1588v2,2 port 10GE + 20 port GE are enabled by default)
					 virent8090DEVCX6D0EMGFA10(564652),   -- V6R6C00 for CX6D0EMGFA10(SBOM),48-Port 100/1000Base-X-SFP Integrated Integrated Service Unit (ISUI-51,Supporting 1588v2)
					 virent8090DEVCX6D0EMGFA1B(564653),   -- V6R6C00 for CX6D0EMGFA1B(SBOM),48-Port 100/1000Base-X-SFP Integrated Integrated Service Unit B(ISUI-51-B,Supporting 1588v2)
					 virent8090DEVCX6D0EFGFA12(564654),   -- V6R6C00 for CX6D0EFGFA12(SBOM),24-Port 100/1000Base-X-SFP Integrated Integrated Service Unit (ISUI-21,Supporting 1588v2)
					 virent8090DEVCX6DL1XEDG1A(564655),   -- V6R6C00 for CX6DL1XEDG1A(SBOM),1-Port 10GBase LAN/WAN-SFP++16-Port 100/1000Base-X-SFP Integrated Integrated Service Unit (ISUI-21,Supporting 1588v2)
					 virent8090DEVLOCALCX6D0L4XXA1B(564656),   -- V6R6C00 for CX6D0L4XXA1B(SBOM),4-Port 10GBase LAN/WAN-XFP Integrated Integrated Service Unit (ISUI-41-B,Supporting 1588v2)
					 virent8090DEVLOCALCX6DL2XEEG1B(564657),   -- V6R6C00 for CX6DL2XEEG1B(SBOM),2-Port 10GBase LAN/WAN-XFP+20-Port 100/1000Base-X-SFP Integrated Integrated Service Unit (ISUI-41-B,Supporting 1588v2)
					 virent8090DEVLOCALCX6D0EKGFA1B(564658),   -- V6R6C00 for CX6D0EKGFA1B(SBOM),40-Port 100/1000Base-X-SFP Integrated Integrated Service Unit (ISUI-41-B,Supporting 1588v2)
					 virent8090DEVCX6DISUFA110(564659),   -- V6R6C00 for CX6DISUFA110(SBOM),Flexible Card Line Processing Unit(ISUF-101,four sub-slots)
					 virent8090DEVCX6D0LAXFA11(564660),   -- V6R6C00 for CX6D0LAXFA11(SBOM),10-Port 10GBase LAN WAN-SFP+ Integrated Integrated Service Unit (ISUI-101,Supporting 1588v2)

					 virent8090DEVCR5D00SNCA00(564606),   --For V600R008C20 VSUF NE SNC Atomic Router
					 virent8090DEVVSUF80(564607),    --SPU2.0 Board(80)
					 virent8090DEVVSUF160(564608),   --SPU2.0 Board(160)
					 virent8090DEVVSUF40(564609),   -- for V600R007C00 CR5DVSUF4010(SBOM), Flexible Card Versatile Service Unit 40(VSUF-40)


					 -- for V800R003C00  NE5000E Manufactured Board
					 virent8090DEVCR5D00EKGF60(564661),   -- 40-Port 1000Base-X-SFP Line Processing Unit (SBOM)
					 virent8090DEVCR5D00P4XX60(564662),   -- 4-Port OC-192c/STM-64c POS-XFP Line Processing Unit E (SBOM)
					 virent8090DEVCR5D00P8UF60(564663),   -- 8-Port OC-48c/STM-16c POS-SFP Line Processing Unit E (SBOM)
					 virent8090DEVCR5D00E4XX60(564664),   -- 4-Port 10GBase LAN-XFP Line Processing Unit E (SBOM)
					 virent8090DEVCR5D00W4XX60(564665),   -- 4-Port 10GBase WAN-XFP Line Processing Unit E (SBOM)
					 virent8090DEVCR5D00LEXF60(564666),   -- 20 port 10GBase LAN/WAN-SFP+ Line Processing Unit(NE5000E LPUI-200) (SBOM)
					 virent8090DEVCR5D00E2NC60(564667),   -- 2-Port 100GBase-CFP Integrated Line Process Unit(NE5000E LPUI-200) (SBOM)
					 virent8090DEVCR5DE1NLAX60(564668),   -- 1 port 100GBase&10 port 10GBase LAN/WAN-SFP+ Line Processing Unit(NE5000E LPUI-200) (SBOM)
					 virent8090DEVCR5D00E1NC60(564669),   -- 1-Port 100GBase-CFP Integrated Line Process Unit(NE5000E LPUI-100) (SBOM)
					 virent8090DEVCR5D00LAXX60(564670),   -- 10-Port 10GBase LAN/WAN-XFP Integrated Line Processing Unit (NE5000E LPUI-100) (SBOM)
					 virent8090DEVCR5DLPUFA060(564671),   -- 100G Flexible Card Line Processing Unit(NE5000E LPUF-100,4 sub-slots) (SBOM)
					 virent8090DEVCR5DSFUIA050(564672),   -- 100G Cluster Central Switch Fabric Unit A(SFUI-100-A) (SBOM)
					 virent8090DEVCR5DSFEBA06B(564673),   -- Switch Fabric Extended Unit B(100G) (SBOM)
					 virent8090DEVCR5D0MPUA450(564674),   -- Central Main Processing Unit A4 (SBOM)
					 virent8090DEVCR5DECUFA050(564675),   -- 100G Cluster Electric Cross Unit A(ECU-100-A) (SBOM)
					 virent8090DEVCR5DSFUFA06B(564676),   -- 100G Switch Fabric Unit B(SFUF-100-B) (SBOM)
					 virent8090DEVCR5D0MPUB461(564677),   -- NetEngine5000E Main Processing Unit B4 (SBOM)
					 virent8090DEVCR5D0MPUA550(564716),   -- NE5000E Main Processing Unit A5(SBOM)
					 virent8090DEVCR5D00ICUB50(564717),   -- NE5000E Internal Communication Unit B(SBOM)
					 virent8090DEVCR5DSFUFK050(564718),   -- 400G Cluster Central Switch Fabric Unit A(SFUF-400-A) (SBOM)
					 virent8090DEVCR5DSFUIK06B(564719),   -- 400G Switch Fabric Unit B for multi Chassis(SFUI-400-B) (SBOM)
					 virent8090DEVCR5DSFUIE060(564678),   -- 200G Switch Fabric Unit B(SFU-200-A) (SBOM)
					 virent8090DEVCR5DSFUIT060(562022),   -- 1T Switch Fabric Unit A for Single Chassis
					 virent8090DEVCR5D00EFMB60(564888),   -- NetEngine5000E,CR56EFMBA0,1000Gbps Line Processing Unit
					 virent8090DEVCR5D00E8NC60(564889),   -- NetEngine5000E,CR56E8NCA0,1000Gbps Line Processing Unit
					 virent8090DEVCR5D0SRUB060(562028),   -- NE5000E-X8 1T Switching and Routing Unit
		virent8090DEVCR5D0SRUB061(562029),   -- NE5000E-X8 400G Switching and Routing Unit
					 virent8090DEVCR5D0SFUT061(562030),   -- NE5000E-X8 1T Switching Fabric Unit for Single Chassis (SFU-1T)
		virent8090DEVCR5D0SFUK061(562031),   -- NE5000E-X8 400G Switching Fabric Unit for Single Chassis (SFU-400)
					 virent8090DEVCR56FRA1TA(562032),   -- NE5000E-X8 1T Switching and Routing Unit
					 -- V6R7 NE&OC CX packing
					 virent8090DEVCR5DL2XEFG7E(564679),    -- V6R7C00 for CR5DL2XEFG7E(SBOM),2-Port 10GBase LAN/WAN-SFP+ + 24-Port 100/1000Base-X-SFP Integrated Line Processing Unit E(LPUI-51-E)
					 virent8090DEVCR5D0L5XFA7E(564680),    -- V6R7C00 for CR5D0L5XFA7E(SBOM),5-Port 10GBase LAN/WAN-SFP+ Integrated Line Processing Unit E(LPUI-51-E)
					 virent8090DEVCR5DLPUFB070(564681),    -- V6R7C00 for CR5DLPUFB070(SBOM),Flexible Card Line Processing Unit(LPUF-120,2 sub-slots)
					 virent8090DEVCR5DLPUFB07B(564682),    -- V6R7C00 for CR5DLPUFB07B(SBOM),Flexible Card Line Processing Unit(LPUF-120,2 sub-slots) B
					 virent8090DEVCR5D0LBXFA70(564683),    -- V6R7C00 for CR5D0LBXFA70(SBOM),12-Port 10GBase LAN/WAN-SFP+ Integrated Line Processing Unit(LPUI-120)
					 virent8090DEVCR5D0E2MCA70(564684),    -- V6R7C00 for CR5D0E2MCA70(SBOM),2-Port 40GBase LAN-CFP Integrated Line Processing Unit(LPUI-120)
					 virent8090DEVCR5D00E1NC76(564685),    -- V6R7C00 for CR5D00E1NC76(SBOM),1-Port 100GBase-CFP Integrated Line Processing Unit (LPUI-120)
					 virent8090DEVCR5D0LBXFA7B(564686),    -- V6R7C00 for CR5D0LBXFA7B(SBOM),12-Port 10GBase LAN/WAN-SFP+ Integrated Line Processing Unit B(LPUI-120-B)
					 virent8090DEVCR5D0E2MCA7B(564687),    -- V6R7C00 for CR5D0E2MCA7B(SBOM),2-Port 40GBase LAN-CFP Integrated Line Processing Unit B(LPUI-120-B)
					 virent8090DEVCR5D00E1NC7B(564688),    -- V6R7C00 for CR5D00E1NC7B(SBOM),1-Port 100GBase-CFP Integrated Line Processing Unit (LPUI-120-B)
					 virent8090DEVCR5DLPUFB07E(564689),    -- V6R7C00 for CR5DLPUFB07E(SBOM),Flexible Card Line Processing Unit(LPUF-120,2 sub-slots) E
					 virent8090DEVCR5D0LAXFA7E(564690),    -- V6R7C00 for CR5D0LAXFA7E(SBOM),10-Port 10GBase LAN/WAN-SFP+ Integrated Line Processing Unit E(LPUI-120-E)
					 virent8090DEVCR5DLPUFF07B(564691),    -- V6R7C00 for CR5DLPUFF07B(SBOM),Flexible Card Line Processing Unit(LPUF-240-B, 2 sub-slots)
					 virent8090DEVCR5DLPUFF070(564692),    -- V6R7C00 for CR5DLPUFF070(SBOM),Flexible Card Line Processing Unit(LPUF-240, 2 sub-slots)
					 virent8090DEVCR5D00E2NC70(564693),    -- V6R7C00 for CR5D00E2NC70(SBOM),2-Port 100GBase-CFP Integrated Line Processing Unit (LPUI-240)
					 virent8090DEVCR5D00LFXF70(564694),    -- V6R7C00 for CR5D00LFXF70(SBOM),24-Port 10GBase LAN/WAN-SFP+ Integrated Line Processing Unit (LPUI-240)
					 virent8090DEVCR5DE2NLBX70(564695),    -- V6R7C00 for CR5DE2NLBX70(SBOM),1-Port 100GBase-CFP + 12-Port 10GBase LAN/WAN-SFP+ Integrated Line Processing Unit (LPUI-240)
					 virent8090DEVCR5D00E2NC73(564696),    -- V6R7C00 for CR5D00E2NC73(SBOM),2-Port 100GBase LAN-CFP Integrated Line Processing Unit B(LPUI-240-B)
					 virent8090DEVCR5D00LFXF73(564697),    -- V6R7C00 for CR5D00LFXF73(SBOM),24-Port 10GBase LAN/WAN-SFP+ Integrated Line Processing Unit B(LPUI-240-B)
					 virent8090DEVCR5DE2NLBX73(564698),    -- V6R7C00 for CR5DE2NLBX73(SBOM),1-Port 100GBase-CFP + 12-Port 10GBase LAN/WAN-SFP+ Integrated Line Processing Unit B(LPUI-240-B)
					 virent8090DEVCR5DLPUFA07J(564699),    -- V6R7C00 for CR5DLPUFA07J(SBOM),Flexible Card Line Processing Unit(LPUF-102,2 sub-slots)
					 virent8090DEVCR5DLPUFA27E(564700),    -- V6R7C00 for CR5DLPUFA27E(SBOM),Flexible Card Line Processing Unit(LPUF-102,2 sub-slots) E
					 virent8090DEVCR5DLPUF517E(564701),    -- V6R7C00 for CR5DLPUF517E(SBOM),Flexible Card Line Processing Unit(LPUF-51,2 sub-slots) E
					 virent8090DEVCR5D0LAXFA7J(564702),    -- V6R7C00 for CR5D0LAXFA7J(SBOM),10-Port 10GBase LAN/WAN-SFP+ Integrated Line Processing Unit (LPUI-102)
					 virent8090DEVCR5DLAXFAJ7E(564703),    -- V6R7C00 for CR5DLAXFAJ7E(SBOM),10-Port 10GBase LAN/WAN-SFP+ Integrated Line Processing Unit E(LPUI-102-E)
					 -- V6R7 NE&OC CX packing
					 -- V6R7 CX60086 packing
					 virent8090DEVCX6DISUFB010(564704),    -- V6R7C00 for CX6DISUFB010(SBOM),Flexible Card Line Processing Unit(ISUF-120,two sub-slots)
					 virent8090DEVCX6D0LBXFA11(564705),    -- V6R7C00 for CX6D0LBXFA11(SBOM),12-Port 10GBase LAN/WAN-SFP+ Integrated Integrated Service Unit (ISUI-120,Supporting 1588v2)
					 -- V6R7 CX60086 packing
					 virent8090DEVCR5DLPUFK061(564706),   -- NE5000E 400G Flexible Card Line Processing Unit(NE5000E LPUF-400,2 sub-slots)
					 virent8090DEVCR5D0MPUB560(564707),   -- NE5000E Main Processing Unit B5
					 --Begin: V6R7 3.28 NE added
					 virent8090DEVCR5DL3XEFG7C(564708),    -- V6R7C00 for CR5DL3XEFG7C(SBOM),3-Port 10GBase LAN/WAN-SFP+ + 24-Port 100/1000Base-X-SFP Integrated Line Processing Unit(LPUI-51)
					 virent8090DEVCR5D0L5XFA7J(564709),    -- V6R7C00 for CR5D0L5XFA7J(SBOM),5-Port 10GBase LAN/WAN-SFP+ Integrated Line Processing Unit E(LPUI-51-E)
					 virent8090DEVCR5DL2XEFG7J(564710),    -- V6R7C00 for CR5DL2XEFG7J(SBOM),2-Port 10GBase LAN/WAN-SFP+ + 24-Port 1000Base-X-SFP Integrated Line Processing Unit E(LPUI-51-E)
					 virent8090DEVCR5D0EMGFA7J(564711),    -- V6R7C00 for CR5D0EMGFA7J(SBOM),48-Port 100/1000Base-X-SFP Integrated Line Processing Unit E(LPUI-51-E)
					 virent8090DEVCR5D0LBXFA7L(564712),    -- V6R7C00 for CR5D0LBXFA7L(SBOM),12-Port 10GBase LAN/WAN-SFP+ Integrated Line Processing Unit L(LPUI-120-L)
					 virent8090DEVCR5D0LAXFA7L(564713),    -- V6R7C00 for CR5D0LAXFA7L(SBOM),10-Port 10GBase LAN/WAN-SFP+ Integrated Line Processing Unit L(LPUI-102-L)
					 virent8090DEVCR5D00LFXF7L(564714),    -- V6R7C00 for CR5D00LFXF7L(SBOM),24-Port 10GBase LAN/WAN-SFP+ Integrated Line Processing Unit L(LPUI-240-L)
					 --End: V6R7 3.28 NE added
					 virent8090DEVCR5D00LMXF61(564715),   -- NE5000E 400G Flexible Card Line Processing Unit(NE5000E LPUI480,2 sub-slots)
		--V6R7 2013.5.6 add by h00205464
		virent8090DEVCR5D0LBXFA71(564720),    -- V6R7C00 for CR5D0LBXFA71(SBOM),12-Port 10GBase LAN/WAN-SFP+ Line Processing Unit(LPUS-120)
		virent8090DEVCX6DSFUIE07B(564721),    -- V6R7C00 for CX6DSFUIE07B(SBOM),200Gbps Switch Fabric Unit B(SFUI-200-B)
		virent8090DEVCX6D0SRUA511(564722),    -- V6R7C00 for CX6D0SRUA511(SBOM),Switch and Route Processing Unit A5
		virent8090DEVCX6DSFUIE07C(564723),    -- V6R7C00 for CX6DSFUIE07C(SBOM),200Gbps Switch Fabric Unit C(SFUI-100-C)
		virent8090DEVCX6DISUFF010(564724),    -- V6R7C00 for CX6DISUFF010(SBOM),Flexible Card Integrated Service Unit(ISUF-240)
		virent8090DEVCX6D0LFXFA10(564725),    -- V6R7C00 for CX6D0LFXFA10(SBOM),24-Port 10GBase LAN/WAN-SFP+ Integrated Integrated Service Unit (ISUI-240,Supporting 1588v2)
		--V6R7 2013.05.10 added by xuelu for X16A
		virent8090DEVCR5DSFUIE07D(564726),    -- V6R7C00 for CR5DSFUIE07D(SBOM),200Gbps Switch Fabric Unit D(SFUI-200-D)
		virent8090DEVCR5DLPUFF07E(564727),    -- V6R7C00 for CR5DLPUFF07E(SBOM),Flexible Card Line Processing Unit(LPUF-240-E)
		-- from 159744 to 659456 is for ME60 Whole BOARD
		virent8090DEVCX6D0LBXFA12(564728),    -- V6R7C00 for CX6D0LBXFA12(SBOM),12-Port 10GBase LAN/WAN-SFP+ Flexible Card A(S240-A)
		 virent8090DEVCX6DL1XESG1A(564730),    -- V6R7C00 for CX6DL1XESG1A(SBOM),1-Port 10GBase LAN/WAN-SFP+ +11-Port 1000Base-X-SFP Flexible Card A(S51-A)
		 virent8090DEVCX6DL2XEAG1A(564731),    -- V6R7C00 for CX6DL2XEAG1A(SBOM),2-Port 10GBase LAN/WAN-SFP+ +10-Port 1000Base-X-SFP Flexible Card A(S51-A)
		virent8090DEVCR5D00LAXF60(564732),    -- 10-Port 10GBase LAN/WAN-SFP+ Integrated Line Processing Unit (NE5000E LPUI-100)
		-- V8R6 2013.11.04 added by caihuali 00240442 for X16A
		virent8090DEVCR5DLPUFM070(564733),    -- V8R6C10 for CR5DLPUFM070(SBOM),Flexible Card Line Processing Unit(LPUF-480)
		--begin : add by liyu for X8A 2013/12/19
		virent8090DEVCR57SRU1TA(564734),    -- V8R6C20 for NE40E CR57SRU1TA
		virent8090DEVCR56SRU1TA(564735),    -- V8R6C20 for NE5000E CR57SRU1TA
		virentCX61DEVCR57SRU1TA(564736),    -- V8R6C20 for OC-CX600 CR57SRU1TA
		virent8090DEVCR57SFU1TC(564737),    -- V8R6C20 for NE40E CR57SFU1TC
		virent8090DEVCR56SFU1TC(564738),    -- V8R6C20 for NE5000E CR56SFU1TC
		virentCX61DEVCR57SFU1TC(564739),    -- V8R6C20 for OC-CX600 CR57SFU1TC
		--end : add by liyu for X8A 2013/12/19
		--Begin: V6R8 2013.11.26 added by yangdi 00238145
		virent8090DEVCR57EBGFD0(564742),      -- V6R8C00 for 12xFE/GE-SFP Fixed Card
		virent8090DEVCR57LAXFB0(564743),      -- V6R8C00 for 10-port 10GBase LAN/WAN-SFP+ Flexible Card
		virent8090DEVCR57L3XFB0(564744),      -- V6R8C00 for 3-port 10GBase LAN/WAN-SFP+ Fixed Card
		virent8090DEVCR57EBGFE0(564745),      -- V6R8C00 for 12xFE-SFP-E Fixed Card
		virent8090DEVCR57L4XFE0(564746),      -- V6R8C00 for 4x10GBase LAN/WAN-SFP+ Fixed Card
		virent8090DEVCR57L3XFE0(564747),      -- V6R8C00 for 3x10GBase LAN/WAN-SFP+ -E Fixed Card
		-- End: V6R8 2013.11.26 added by yangdi 00238145
		--V6R8 added h00205464
		virent8090DEVCR5DL3XEFG7E(564748),   -- V6R8C00 for CR5DL3XEFG7E(SBOM),3-Port 10GBase LAN/WAN-SFP+ + 24-Port 1000Base-X-SFP Integrated Line Processing Unit E(LPUI-51-E)
		virent8090DEVCR5DL4XEBG7E(564749),   -- V6R8C00 for CR5DL4XEBG7E(SBOM),4-Port 10GBase LAN/WAN-SFP+ + 12-Port 1000Base-X-SFP Integrated Line Processing Unit E(LPUI-51-E)
		 virent8090DEVCR5DL4XEBG7L(564750),   -- V6R8C00 for CR5DL4XEBG7L(SBOM),4-Port 10GBase LAN/WAN-SFP+ + 12-Port 100/1000Base-X-SFP Integrated Line Processing Unit L(LPUI-51-L)
		 virent8090DEVCR5D0MPUD270(564751),   -- V6R8C00 for CR5D0MPUD270(SBOM),Main Processing Unit D3
		virent8090DEVCR2D000MPU11(564752),   -- V6R8C00 for CR2D000MPU11(SBOM),Main Processing Unit 2
		virent8090DEVCR2DLPUF5010(564753),   -- V6R8C00 for CR2DLPUF5010(SBOM),Flexible Card Line Processing Unit(NE20E LPUF-50,four slots)
		virent8090DEVCR21LPU50A00(564754),   -- V6R8C00 for CR21LPU50A00(SBOM),FIC Service Processing Engine(NE20E-X6,four slots)
		virent8090DEVCR5DL4XEBG7C(564755),   -- V6R8C00 for CR5DL4XEBG7C(SBOM),4-Port 10GBase LAN/WAN-SFP+ + 12-Port 100/1000Base-X-SFP Integrated Line Processing Unit (LPUI-51)
		virent600DEVCX6D0MPUD270(564756),   -- V6R8C00 for CX6D0MPUD270(SBOM),Main Processing Unit D3
		virent8090DEVCR2D0EMGFA1L(564757),   -- V6R8C00 for CR2D0EMGFA1L(SBOM),48-Port 100/1000Base-X-SFP Integrated Line Processing Unit L(LPUI-51-L)
		virent8090DEVCR5D0SRUA870(564758),   -- V8R6C20 for CR5D0SRUA870(SBOM), Switch and Route Processing Unit A8
		virent8090DEVCR5DSFUIM07C(564759),   -- V8R6C20 for CR5DSFUIM07C(SBOM), 480Gbps Switch Fabric Unit C(SFUI-480-C)
		virent8090DEVCR5DSFUIU07B(564760),   -- V8R6C20 for CR5DSFUIU07B(SBOM), 1Tbps Switch Fabric Unit B(SFUI-1T-B)
		virent8090DEVCR5DSFUIM07B(564761),   -- V8R6C20 for CR5DSFUIM07B(SBOM), 480Gbps Switch Fabric Unit B(SFUI-480-B),V8R6C10 shen qing de zhi mei you lu ru, chong xin shen qing yi ci
		virent600DEVCX6D0SRUA870(564762),    -- V8R6C20 for CX6D0SRUA870(SBOM), Switch and Route Processing Unit A8
		virent600DEVCX6DSFUIM07C(564763),    -- V8R6C20 for CX6DSFUIM07C(SBOM), 480Gbps Switch Fabric Unit C(SFUI-480-C)
		virent600DEVCX6D0MPUB570(564764),    -- V8R6C20 for CX6D0MPUB570(SBOM), Main Processing Unit B5
		virent600DEVCX6DSFUIM07B(564765),    -- V8R6C20 for CX6DSFUIM07B(SBOM), 480Gbps Switch Fabric Unit B(SFUI-480-B)
		virent600DEVCX6DSFUIU07B(564766),    -- V8R6C20 for CX6DSFUIU07B(SBOM), 1Tbps Switch Fabric Unit B(SFUI-1T-B)
		virent600DEVCX6PM2EBAS70(564767),    -- V8R6C20 V8R7 for CX67MNPUI(SBOM), 80Gbps MNPUI DC
		virent600DEVCX6PM2EBAS71(564802),    -- V8R6C20 V8R7 for CX67MNPUI(SBOM), 80Gbps MNPUI AC
		virent600DEVCX6PM2FBAS70(564785),    --V8R6C20 V8R7 CX600-M2F CX67MNPUI(SBOM), 160Gbps MNPUI DC
		virent600DEVCX6PM2FBAS71(564786), 	 --V8R6C20 V8R7 CX600-M2F CX67MNPUI(SBOM), 160Gbps MNPUI AC
		virent600DEVCR2P2EBASD10(564787),  	 --V8R6C20 V8R7 NE20E-S2E CX67MNPUI(SBOM), 80Gbps MNPUI DC
		virent600DEVCR2P2EBASA10(564788),    --V8R6C20 V8R7 NE20E-S2E CX67MNPUI(SBOM), 80Gbps MNPUI AC
		virent600DEVCR2P2FBASD10(564789),    --V8R6C20 V8R7 NE20E-S2F CX67MNPUI(SBOM), 160Gbps MNPUI DC
		virent600DEVCR2P2FBASA10(564790),    --V8R6C20 V8R7 NE20E-S2F CX67MNPUI(SBOM), 160Gbps MNPUI AC
		virent600DEVCR5PM2EBAS70(564791),  	 --V8R6C20 V8R7 NE40E-M2E CX67MNPUI(SBOM), 80Gbps MNPUI DC
		virent600DEVCR5PM2EBAS71(564792),  	 --V8R6C20 V8R7 NE40E-M2E CX67MNPUI(SBOM), 80Gbps MNPUI AC
		virent600DEVCR5PM2FBAS70(564793),    --V8R6C20 V8R7 NE40E-M2F CX67MNPUI(SBOM), 160Gbps MNPUI DC
		virent600DEVCR5PM2FBAS71(564794), 	 --V8R6C20 V8R7 NE40E-M2F CX67MNPUI(SBOM), 160Gbps MNPUI AC
		virent600DEVTNRPM2EBAS70(564795), 	 --V8R6C20 V8R7 PTN6900-M2E CX67MNPUI(SBOM), 80Gbps MNPUI DC
		virent600DEVTNRPM2EBAS71(564796), 	 --V8R6C20 V8R7 PTN6900-M2E CX67MNPUI(SBOM), 80Gbps MNPUI AC
		virent600DEVTNRPM2FBAS70(564797), 	 --V8R6C20 V8R7 PTN6900-M2F CX67MNPUI(SBOM), 160Gbps MNPUI DC
		virent600DEVTNRPM2FBAS71(564798), 	 --V8R6C20 V8R7 PTN6900-M2F CX67MNPUI(SBOM), 160Gbps MNPUI AC
		  virent8090DEVCX68FCBD(564799),       --V8R6C20 V8R7 M2 fan unit
		virent8090DEVCX68PSUF(564800),       --V8R6C20 V8R7 M2 DC power supply unit
		virent8090DEVCX68PSUG(564801),       --V8R6C20 V8R7 M2 AC power supply unit
		--BEGIN: for V6R8C10 by w00195304
		virent600DEVCX6DL2XEEG7B(564774),   -- V6R8C10 for CX6DL2XEEG7B(SBOM),2-Port 10GBase LAN/WAN-XFP+20-Port 100/1000Base-X-SFP Integrated Integrated Service Unit (ISUI-51-B,Supporting 1588v2)
		virent8090DEVCR5D0E6MFA70(564775),    -- V6R8C10 for CR5D0E6MFA70(SBOM), 6-Port 40GBase-QSFP+ Integrated Line Processing Unit (LPUI-240)
		virent8090DEVCR5D0E6MFA71(564776),    -- V6R8C10 for CR5D0E6MFA71(SBOM), 6-Port 40GBase-QSFP+ Integrated Line Processing Unit (LPUI-240-B)
		virent600DEVCX6DISUFE011(564777),    -- V6R8C10 for CX6DISUFE011(SBOM), Flexible Card Integrated Service Unit(ISUF-200)
		virent600DEVCX6DISUFA210(564778),    -- V6R8C10 for CX6DISUFA210(SBOM), Flexible Card Integrated Service Unit(ISUF-102)
		virent600DEVCX6D0LEXFA10(564779),    -- V6R8C10 for CX6D0LEXFA10(SBOM), 20-Port 10GBase LAN/WAN-SFP+ Integrated  Integrated Service Unit (ISUI-200,Supporting 1588v2)
		virent600DEVCX6D0LAXFA10(564780),    -- V6R8C10 for CX6D0LAXFA10(SBOM), 10-Port 10GBase LAN/WAN-SFP+ Integrated  Integrated Service Unit (ISUI-102,Supporting 1588v2)
		--END: for V6R8C10 by w00195304
		--BEGIN: for V6R8C10 by s00201944
		virent600DEVCX6DVSUI2010(564781),    -- V6R8C10 for CX6DVSUI2010(SBOM), Integrated Versatile Service Unit(VSUI-20)
		--END: for V6R8C10 by s00201944

		virent8090DEVCR5D00LMXF70(564782),    -- V8R6C10 for CR5D00LMXF70(SBOM),48-Port 10GBase LAN/WAN-SFP+ Integrated Line Processing Unit (LPUI-480)
		virent8090DEVCR5DE2NLFX70(564783),    -- V8R6C10 for CR5DE2NLFX70(SBOM),2-Port 100GBase-CFP2 + 24-Port 10GBase LAN/WAN-SFP+ Integrated Line Processing Unit (LPUI-480)
		virent8090DEVCR5D00E4NC70(564784),    -- V8R6C20 for CR5D00E4NC70(SBOM),4-Port 100GBase-CFP2 Integrated Line Processing Unit (LPUI-480)
		virent8090DEVCR5DOMPUB061(564901),   -- V8R7C00 for CR5DOMPUB061(SBOM), -16 Main Processing Uint
		virent600DEVCX62SNCA00(564803),       -- V600R008C20 for VSUF CH-CX SNC Atomic Router

		--V8R7 2014.06.13 added by raopeitao for lpu1te
		virent8090DEVCR5D00E8NC70(564740),    -- V8R7C00 for CR5D00E8NC70(SBOM),8-Port 100GBase-CFP2 Integrated Line Processing Unit (LPUI-1T)
 -- ME60:
					 virentME60DEVLPU(159744),            -- The whole IO board, incude all entitys on the slot
					 virentME60DEVMPU(159745),            -- Whole MPU Board, incude all entitys on the slot, virtual entity
					 virentME60DEVSRU(159746),            -- Whole SRU Board, incude all entitys on the slot, virtual entity
					 virentME60DEVSFUA(159747),           -- Switch Fabric Unit for Full Capacity System, incude all entitys on the slot,virtual entity
					 virentME60DEVSFUB(159748),           -- Switch Fabric Unit for Half & Halflow Frame System, incude all entitys on the slot,virtual entity

					 -- from 159749 to 160499 is for ME60 MPU Whole board
					 virentME60DEVCR52SRUA(159749),       -- the old whole board of SRUA saled before V3R8 version in ME60(whithout SBOM information)
					 virentME60DEVCR52MPUA(159750),       -- the old whole board of MPUA saled before V3R8 version in ME60(whithout SBOM information)
					 virentME60DEVCR52MPUB(159751),       -- the old whole board of MPUB saled before V3R8 version in ME60(whithout SBOM information)

					 virentME60DEVME0D00MPUD70(159752),   -- V3R8 for ME0D00MPUD70(SBOM), ME60-X3 Main Processing Unit D
					 virentME60DEVME03SRUA3(159753),      -- V3R8 for ME03SRUA3(SBOM), ME60-8 Switch and Route Processing Unit A3
					 virentME60DEVME0D0SRUA470(159754),   -- V3R8 for ME0D0SRUA470(SBOM), ME60-X16 Main Processing Unit B4
					 virentME60DEVME03MPUA0(159755),      -- V3R8 for ME03MPUA0(SBOM), ME60-16 Main Processing Unit A0
					 virentME60DEVME0D0MPUB470(159756),   -- V3R8 for ME0D0MPUB470(SBOM), ME60-X8 Switch and Route Processing Unit A4
					 virentME60DEVME0D00MPUH(159757),     -- V6R5 for ME0D00MPUH(SBOM), ME60-X3 Main Processing Unit H
					 virentME60DEVME03SRU200A5(159798),   -- V6R3C05 for ME03SRU200A5(SBOM),Switch and Route Processing Unit A5(Including 1*2G Memory and 1*1G CF Card)

					 -- from 160500 to 161499 is for ME60 SFU Whole board
					 virentME60DEVCR52SFUA(160500),          -- the old whole board of SFUA saled before V3R8 version in ME60(whithout SBOM information)
					 virentME60DEVCR52SFUD(160501),           -- the old whole board of SFUD saled before V3R8 version in ME60(whithout SBOM information)
					 virentME60DEVCR52SFUF(160502),           -- the old whole board of SFUF saled before V3R8 version in ME60(whithout SBOM information)
					 virentME60DEVCR52SFUG(160503),           -- the old whole board of SFUG saled before V3R8 version in ME60(whithout SBOM information)

					 virentME60DEVME0DSFUI407B(160504),   -- V3R8 for ME0DSFUI407B(SBOM), ME60-X16 40G Switch Fabric Unit B
					 virentME60DEVME0DSFUI407C(160505),   -- V3R8 for ME0DSFUI407C(SBOM), ME60-X8 40G Switch Fabric Unit C
					 virentME60DEVME0D00SFUG20(160506),   -- V3R8 for ME0D00SFUG20(SBOM), ME60-16 Switch Fabric Unit G
					 virentME60DEVME03SFU200B0(160507),   -- V6R3C05 for ME03SFU200B0(SBOM),200Gbps Switch Fabric Unit B(SFUI-200-B)
					 virentME60DEVME03SFU200C0(160508),   -- V6R3C05 for ME03SFU200C0(SBOM),200Gbps Switch Fabric Unit C(SFUI-200-C)
					 -- V6R7 packing for mpu 2012-12-09 begin
					 virentME60DEVSRU100D(160509),     -- V6R7C00,SRU100D,Switch and Route Processing Unit A7(Including 1*2G Memory and 1*1G CF Card)
					 virentME60DEVSFU100D(160510),     -- V6R7C00,SFU100D,100Gbps Switch Fabric Unit D(SFUI-100-D)
					 virentME60DEVME0DSFUIE07D(160511),     -- V6R7C00,ME0DSFUIE07D(SBOM),100Gbps Switch Fabric Unit B(SFUI-100-B)
					 -- V6R7 packing for mpu 2012-12-09 end

					 -- from 161500 to 162999 is for ME60 LPU Whole board
					 virentME60DEVCR52BSUA(161500),       -- the old whole board of BSUA(CR52LPUA) saled before V3R8 version in ME60(whithout SBOM information)
					 virentME60DEVCR52MSUA(161501),       -- obsolete,
					 virentME60DEVCR52SSUA(161502),       -- the old whole board of SSUA(CR52LPUA) saled before V3R8 version in ME60(whithout SBOM information)
					 virentME60DEVCR52SCUA(161503),       -- the old whole board of SCUA(CR52LPUA) saled before V3R8 version in ME60(whithout SBOM information)
					 virentME60DEVCR52TSUA(161504),       -- the old whole board of TSUA(CR52LPUA) saled before V3R8 version in ME60(whithout SBOM information)
					 virentME60DEVCR52DSUA(161505),       -- the old whole board of DSUA(CR52LPUA) saled before V3R8 version in ME60(whithout SBOM information)
					 virentME60DEVCR52NSUA(161506),       -- obsolete,
					 virentME60DEVCR52ESUA(161507),       -- the old whole board of ESUA(CR52LPUA) saled before V3R8 version in ME60(whithout SBOM information)
					 virentME60DEVME01BSUA(161508),       -- the old whole board of BSUA(ME01LPUA) saled before V3R8 version in ME60(whithout SBOM information)
					 virentME60DEVME01MSUA(161509),       -- the old whole board of MSUA(ME01LPUA) saled before V3R8 version in ME60(whithout SBOM information)
					 virentME60DEVME01SSUA(161510),       -- obsolete,
					 virentME60DEVME01SCUA(161511),       -- obsolete,
					 virentME60DEVME01TSUA(161512),       -- obsolete,
					 virentME60DEVME01DSUA(161513),       -- obsolete,
					 virentME60DEVME01NSUA(161514),       -- obsolete,
					 virentME60DEVME01VSUA(161515),       -- the old whole board of VSUA(ME01LPUA) saled before V3R8 version in ME60(whithout SBOM information)

					 virentME60DEVME03BSUF10(161516),     -- V3R8 for ME03BSUF10(SBOM), Flexible Card Broadband Service Unit(BSUF-10,four sub-slots)
					 virentME60DEVME0MBSUF2120(161517),   -- V3R8 for ME0MBSUF2120(SBOM), Flexible Card Broadband Service Unit(BSUF-21,2 sub-slots)
					 virentME60DEVME03MSUF21(161518),     -- V3R8 for ME03MSUF21(SBOM), Flexible Card Multi Service Unit(MSUF-21,2 sub-slots)
					 virentME60DEVME0MMSUF4020(161519),   -- V3R8 for ME0MMSUF4020(SBOM), Flexible Card Multi Service Unit(MSUF-40,2 sub-slots)
					 virentME60DEVME03SPUC(161520),       -- V3R8 for ME03SPUC(SBOM), Versatile Service Process Unit C
					 virentME60DEVME0MVSUF1010(161521),   -- V3R8 for ME0MVSUF1010(SBOM), Flexible Card Versatile Service Unit 10(VSUF-10)
					 virentME60DEVME0MBSUF4020(161522),   -- V3R8 for ME0MBSUF4020(SBOM), Flexible Card Broadband Service Unit(BSUF-40,2 sub-slots)
					 virentME60DEVME0MMSUF1010(161523),   -- V3R8 for ME0MMSUF1010(SBOM), Flexible Card Multi Service Unit(MSUF-10,2 sub-slots)
					 virentME60DEVME0MVSUI201A(161524),   -- V3R8 for ME0MVSUI201A(SBOM), Integrated Versatile Service Unit 20 A(VSUI-20-A)
					 virentME60DEVME0MWSUF2120(161525),   -- V6R2C09 for ME0MWSUF2120(SBOM),Flexible Card WLAN Service Unit(WSUF-21,2 sub-slots)
					 virentME60DEVME03MSUF100(161526),   -- V6R3C05 for ME03MSUF100(SBOM),Flexible Card Multi Service Unit (MSUF-100,4 sub-slots)
					 virentME60DEVME03LAXXB0(161527),   -- V6R3C05 for ME03LAXXB0(SBOM),10-Port 10GBase LAN/WAN-XFP Multi Service Unit Integrated (MSUI-100)
					 virentME60DEVME03VSUI20A(161528),   -- V6R3C05 for CR5DME03VSUI20A(SBOM),Integrated Versatile Service Unit 20 A(VSUI-20-A)
					 virentME60DEVME03E1NC0(161529),   -- V6R3C05 for ME03E1NC0(SBOM),1-Port 100GBase-CFP Multi Service Unit Integrated (MSUI-100)
					 virentME60DEVME0D0EKGFE70(161530),   -- for V600R005C00 ME0D0EKGFE70(SBOM),40-Port 100/1000Base-SFP Broadband Service Unit Integrated(BSUI-40)
					 virentME60DEVME0D0L4XXE70(161531),   -- for V600R005C00 ME0D0L4XXE70(SBOM),4-Port 10GBase LAN/WAN-XFP Broadband Service Unit Integrated(BSUI-40)
					 virentME60DEVME0DL2XEEG7E(161532),   -- for V600R005C00 ME0DL2XEEG7E(SBOM),2-Port 10GBase LAN/WAN-XFP+20-Port 100/1000Base-SFP Broadband Service Unit Integrated(BSUI-40)
					 virentME60DEVME0D0L4XXB70(161533),   -- for V600R005C00 ME0D0L4XXB70(SBOM),4-Port 10GBase LAN/WAN-XFP Multi Service Unit Integrated(MSUI-40)
					 virentME60DEVME0D0EEGFE20(161534),   -- for V600R005C00 ME0D0EEGFE20(SBOM),20-Port 100/1000Base-SFP Broadband Service Unit Integrated(BSUI-21)
					 virentME60DEVME0D0L2XXE20(161535),   -- for V600R005C00 ME0D0L2XXE20(SBOM),2-Port 10GBase LAN/WAN-XFP Broadband Service Unit Integrated(BSUI-21)
					 virentME60DEVME0DEBGE1X20(161536),   -- for V600R005C00 ME0DEBGE1X20(SBOM),1-Port 10GBase LAN/WAN-XFP+10-Port 100/1000Base-X-SFP Broadband Service Unit Integrated(BSUI-21)
					 virentME60DEVME0D0L2XXB70(161537),   -- for V600R005C00 ME0D0L2XXB70(SBOM),2-Port 10GBase LAN/WAN-XFP Multi Service Unit Integrated(MSUI-21)
					 virentME60DEVME0D0EFGFB50(161538),   -- for V600R005C00 ME0D0EFGFB50(SBOM),24-Port 100/1000Base-X-SFP Broadband Service Unit Integrated(BSUI-22)
					 virentME60DEVME0D0L2XXB50(161539),   -- for V600R005C00 ME0D0L2XXB50(SBOM),2-Port 10GBase WAN/LAN-XFP Broadband Service Unit Integrated(BSUI-22)
					 virentME60DEVMEODE1XEBG50(161540),   -- for V600R005C00 MEODE1XEBG50(SBOM),1-Port 10GBase WAN/LAN-XFP+12-Port 100/1000Base-X-SFP Broadband Service Unit Integrated(BSUI-22)
					 virentME60DEVME0D0L4XXB50(161541),   -- for V600R005C00 ME0D0L4XXB50(SBOM),4-Port 10GBase WAN/LAN-XFP Broadband Service Unit Integrated(BSUI-41)
					 virentME60DEVME0D0EKGFE50(161542),   -- for V600R005C00 ME0D0EKGFE50(SBOM),40-Port 100/1000Base-X-SFP Broadband Service Unit Integrated(BSUI-41)
					 virentME60DEVME0DL2XEEG50(161543),   -- for V600R005C00 ME0DL2XEEG50(SBOM),2-Port 10GBase WAN/LAN-XFP+20-Port 100/1000Base-X-SFP Broadband Service Unit Integrated(BSUI-41)
					 virentME60DEVVSUF80(161544),         ---SPU2.0 Board(80)
					 virentME60DEVVSUF160(161545),        --SPU2.0 Board(160)
					 --- V6R7 ME packing 2012-10-11 begin
					 virentME60DEVME0DBSUF5170(161546),   -- for V600R007C00 ME0DBSUF5170(SBOM),Flexible Card Broadband Service Unit(BSUF-51,2 sub-slots)
					 virentME60DEVME0DL2XEFG7E(161547),   -- for V600R007C00 ME0DL2XEFG7E(SBOM),2-Port 10GBase LAN/WAN-XFP++24-Port 1000Base-SFP Broadband Service Unit Integrated E(BSUI-51-E)
					 virentME60DEVME0DL2XEFG7B(161548),   -- for V600R007C00 ME0DL2XEFG7B(SBOM),2-Port 10GBase LAN/WAN-XFP++24-Port100/1000Base-SFP Broadband Service Unit Integrated (BSUI-51)
					 virentME60DEVME0D0L5XXE70(161549),   -- for V600R007C00 ME0D0L5XXE70(SBOM),5-Port 10GBase WAN/LAN-XFP Broadband Service Unit Integrated E(BSUI-51-E)
					 virentME60DEVME0D0L5XXB70(161550),   -- for V600R007C00 ME0D0L5XXB70(SBOM),5-Port 10GBase WAN/LAN-XFP Broadband Service Unit Integrated(BSUI-51)
					 virentME60DEVME0DMSUF5170(161551),   -- for V600R007C00 ME0DMSUF5170(SBOM),Flexible Card Multi Service Unit(MSUF-51,2 sub-slots)
					 virentME60DEVME0D0L5XXM70(161552),   -- for V600R007C00 ME0D0L5XXM70(SBOM),5-Port 10GBase WAN/LAN-SFP+ Multi Service Unit Integrated(MSUI-51)
					 virentME60DEVME0DBSUFA070(161553),   -- for V600R007C00 ME0DBSUFA070(SBOM),Flexible Card Broadband Service Unit(BSUF-100,2 sub-slots)
					 virentME60DEVME0DMSUFA070(161554),   -- for V600R007C00 ME0DMSUFA070(SBOM),Flexible Card Multi Service Unit(MSUF-100,2 sub-slots)
					 virentME60DEVME0D0LAXXE70(161555),   -- for V600R007C00 ME0D0LAXXE70(SBOM),10-Port 10GBase WAN/LAN-SFP+ Broadband Service Unit Integrated E(BSUI-100-E)
					 virentME60DEVME0D0L1NXM70(161556),   -- for V600R007C00 ME0D0L1NXM70(SBOM),1-Port 100GBase WAN/LAN-XFP Multi Service Unit Integrated(MSUI-100)
					 virentME60DEVME0DBSUFF070(161557),   -- for V600R007C00 ME0DBSUFF070(SBOM),Flexible Card Broadband Service Unit(BSUF-240,2 sub-slots)
					 --- V6R7 ME packing 2012-10-11 end
					 --- V6R7 ME packing 2013-03-28 begin
					 virentME60DEVME0DL3XEFG7B(161558),   -- for V600R007C00 ME0DL3XEFG7B(SBOM),3-Port 10GBase LAN/WAN-SFP++24-Port100/1000Base-SFP Broadband Service Unit Integrated (BSUI-51)
					 virentME60DEVME0D0EMGFB70(161559),   -- for V600R007C00 ME0D0EMGFB70(SBOM),48-Port100/1000Base-SFP Broadband Service Unit Integrated (BSUI-51)
					 virentME60DEVME0D0LAXXB70(161560),   -- for V600R007C00 ME0D0LAXXB70(SBOM),10-Port 10GBase LAN/WAN-SFP+ Broadband Service Unit Integrated(BSUI-100)
					 virentME60DEVME0D0LBXFA70(161561),   -- for V600R007C00 ME0D0LBXFA70(SBOM),12-Port 10GBase LAN/WAN-SFP+ Broadband Service Unit Integrated(BSUI-100)
					 virentME60DEVME0D0LBXXA70(161562),   -- for V600R007C00 ME0D0LBXXA70(SBOM),12-Port 10GBase LAN/WAN-XFP Broadband Service Unit Integrated(MSUI-100)
					 --- V6R7 ME packing 2013-03-28 end
		--- V6R7 V6R7 2013.5.6 add by h00205464
		virentME60DEVME0D0LAXFA70(161563),   -- for V600R007C00 ME0D0LAXFA70(SBOM),10-Port 10GBase LAN/WAN-SFP+ Broadband Service Unit Integrated(MSUI-100)
				  virentME60DEVVSUF40(161564),         ---for V600R007C00 ME0DVSUF4070(SBOM), Flexible Card Versatile Service Unit 40(VSUF-40)
				virentME0DL4XEBG7B(161565),          ---for V600R008C00 ME0DL4XEBG7B(SBOM), 4-Port 10GBase LAN/WAN-SFP++12-Port100/1000Base-SFP Broadband Service Unit Integrated (BSUI-51)
				virentME0DMSUFF070(161566),          ---for V600R008C00 ME0DMSUFF070(SBOM), Flexible Card Multi Service Unit(MSUF-240,2 sub-slots)
				virentME0D00MPUD72(161567),			 ---for V600R008C00 ME0D00MPUD72(SBOM),Main Processing Unit D3

--	BGW			Add for BGW series V6R8C10
				fnameBGW9916(561190),                -- BGW9916 FRAME
				virentBGW9916DEVBGWD0MPUB470(161568),			 ---for V600R008C10 BGWD0MPUB470(SBOM),BGW9916 Main Processing Unit B4
				virentBGW9916DEVBGWDSFUIE07B(161569),			 ---for V600R008C10 BGWDSFUIE07B(SBOM),200Gbps Switch Fabric Unit B(SFUI-200-B)
				virentBGW9916DEVBGWDBPUFA070(161570),			 ---for V600R008C10 BGWDBPUFA070(SBOM),Flexible Card Bonding Processing Unit(BPUF-100)
				virentBGW9916DEVBGWDBPUFC870(161571),			 ---for V600R008C10 BGWDBPUFC870(SBOM),Flexible Card Bonding Processing Unit(BPUF-200)
				virentBGW9916DEVBGWDASUFD070(161572),     -- for V600R008C10 BGWDASUFD070(SBOM), Flexible Card Aggregation Service Unit 160(ASUF-160)
				subbnameBGW9916DEVBGWD00SPD070(161573),   -- for V600R008C10 BGWD00SPD070(SBOM), Aggregation Service Daught Card(SP160)
				subbnameBGW9916DEVBGWD0L5XF070(161574),   -- for V600R008C10 BGWD0L5XF070(SBOM), 5-Port 10GBase LAN/WAN-SFP+ Flexible Card(BP100)
				subbnameBGW9916DEVBGWD0EFGF070(161575),   -- for V600R008C10 BGWD0EFGF070(SBOM), 24-Port 100/1000Base-X-SFP Flexible Card(BP100)
				subbnameBGW9916DEVBGWD0LAXF070(161576),   -- for V600R008C10 BGWD0LAXF070(SBOM), 10-Port 10GBase LAN/WAN-SFP+ Flexible Card(BP200)
				virentME60DEVME0D00SNCA00(161578),        -- for V600R008C20 VSUF ME SNC Atomic Router

					 -- from 163000 to 163499 is for ME60 OTHER Whole board
					 virentME60DEVFCARD(163000),          -- the old whole board of Flex-card saled before V3R8 version in ME60(whithout SBOM information)
-- atn
					 virentATNDEVANE7MPUG0(225280),     -- Main Processing Unit G(Including 1*1G CF Card)
					 virentATNDEVANE7NPUI20(225281),    -- Network Processing Unit Integrated with 2-Port 10GBase LAN/WAN-XFP
					 virentATNDEVANE7PIUD0(225282),    -- Power Supply Unit
--ATN910&950, ATN950B

					virentATNBoard(225290),          --Unknown board type
					virentATNCXPG(225291),           --System control, switching and timing board, with 4x FE service interfaces, 2x GE service interfaces, and 16x E1 interfaces (matching 75-ohm E1)
					virentATNCXPH(225292),           --System control, switching and timing board, with 4x FE service interfaces, 2x GE service interfaces, and 16x E1 interfaces (matching 120-ohm E1)
					virentATNCXPI(225293),           --System control, switching and timing board, with 8x FE service interfaces, 2x GE service interfaces
					virentATNCXP(225294),             --System control, switching and timing board
					virentATNCXPA(225475),            --System control, switching and timing board for ATN950B
					virentATNCXPB(225476),            --System control, switching and timing board for ATN950B
					virentATNCXPC(225478),            --System control, switching and timing board for ATN950B
					virentATNC2CXPL(225493),         --System control, switching and timing board, with 2GE(o),4GE/FE(o),4GE/FE(e)
					virentATNC2CXPI(225501),         --System control, switching and timing board, with 2GE(o),4FE(o),4FE(e)
					virent910I-AC(225484),           --System control, switching and timing board, with 4GE(o),4GE/FE(o),4GE/FE(e),AC POWER
					virent910I-DCA(225485),           --System control, switching and timing board, with 4GE(o),4GE/FE(o),4GE/FE(e),DC POWER
					virent910I-DCB(225486),           --System control, switching and timing board, with 16E1,4GE(o),4GE/FE(o),4GE/FE(e),DC POWER
					virent910I-C-ACA(225487),         --System control, switching and timing board, with 16E1,4GE(o),4GE/FE(o),4GE/FE(e),AC POWER,support 1588ACR
					virent910I-TC-DC(225488),        --System control, switching and timing board, with 16E1,4GE(o),4GE/FE(o),4GE/FE(e),DC POWER,support 1588ACR,heat box
					virent910I-DCC(225489),           --System control, switching and timing board, with 16E1,4GE(o),4GE/FE(o),4GE/FE(e),4FE,DC POWER
					virent910I-C-ACB(225498),         --System control, switching and timing board, with 16E1,2GE(o),4GE/FE(o),4GE/FE(e),AC POWER,support 1588ACR
					virent910I-DCD(225499),           --System control, switching and timing board, with 16E1,2GE(o),4GE/FE(o),4GE/FE(e),DC POWER
					virent910I-C-ACC(225502),         --System control, switching and timing board, with 16E1,4GE(o),4FE(o),2GE/FE(e),2FE(e),AC POWER,support 1588ACR
					virent910I-DCE(225503),           --System control, switching and timing board, with 16E1,4GE(o),4FE(o),2GE/FE(e),2FE(e),4FE(e),DC POWER
					virent910I-P-AC(225511),         --System control, switching and timing board, with 4GE(o),4GE/FE(o),4GE/FE(e),poe
					virentANP1CXPC(225512),           --System control, switching and timing board, with 2Combo,2GE/FE (o),2GE/FE(e)
					virentANP1CXPD(225513),         --System control, switching and timing board, with 2Combo,2GE(o),2GE/FE(o)
					virentANP1CXPE(225514),           --System control, switching and timing board, with 1Combo,1GE/FE (o),2GE/FE(e),poe

 -- PTN:
					virentPTN6900DEVTNR1SCAB(229376),    --Main Processing Unit B4(Including 1*2G Memory and 1*1G CF Card)

					virentPTN6900DEVTNR1XCS40B(229377),  --40Gbps Switch Fabric Unit B
					virentPTN6900DEVTNR1XCS200B(229378), --200Gbps Switch Fabric Unit B
					virentPTN6900DEVTNR1XCS40C(229379),  --40Gbps Switch Fabric Unit C
					virentPTN6900DEVTNR1XCS200C(229380), --200Gbps Switch Fabric Unit C
					virentPTN6900DEVTNR1SCA40C(229381),    --Switch and Route Processing Unit A2(Supporting 1588v2)
					virentPTN6900DEVTNR1EX8B(229382),    --8-Port 10GBase LAN/WAN-XFP Integrated Service Unit
					virentPTN6900DEVTNR1EX4(229383),     --4-Port 10GBase LAN/WAN-XFP Integrated Service Unit (Supporting 1588v2)
					virentPTN6900DEVTNR1EX4B(229384),    --4-Port 10GBase LAN/WAN-XFP Integrated Service Unit
					virentPTN6900DEVTNR1EG48B(229385),   --48-Port 100/1000Base-X-SFP Integrated Service Unit
					virentPTN6900DEVTNR1EM40(229386),    --2-Port 10GBase LAN/WAN-XFP+24-Port 100/1000Base-X-SFP Integrated Service Unit
					virentPTN6900DEVTNR1EM40B(229387),   --2-Port 10GBase LAN/WAN-XFP+24-Port 100/1000Base-X-SFP Integrated Service Unit
					virentPTN6900DEVTNR1EG40(229388),    --40-Port 100/1000Base-X-SFP Integrated Service Unit (Supporting 1588v2)
					virentPTN6900DEVTNR1MEPF40(229389),  --Flexible Card Integrated Service Unit(four sub-slots)
					virentPTN6900DEVTNR1MEPF10(229390),  --Flexible Card Integrated Service Unit(two sub-slots)
					--for PTN6900-ChinaMobile
					virentPTN6900DEVTNRD00EX1000(229391), --10 Ports 10 Gigabit Ethernet Processing Board (Supporting 1588V2)
					virentPTN6900DEVTNRD0EX16B00(229392),    --16 Ports 10 Gigabit Ethernet Processing Board
					virentPTN6900DEVTNR1SCA200C(229393),   --200G System Control,Communication and Auxiliary Process Unit C (Including 1*2G Memory and 2*1G CF Card)
					virentPTN6900DEVTNR1CMUA(229394),    --Centralized Monitor Unit

					--for VFD
					virentPTN6900DEVTNR1SFU40B0(229395),    --40Gbps Switch Fabric Unit B
					virentPTN6900DEVTNR1SRU40A4(229396),    --Switch and Route Processing Unit A4(Including 1*2G Memory and 2*1G CF Card)
					virentPTN6900DEVTNR1SFU40C0(229397),    --40Gbps Switch Fabric Unit C
					virentPTN6900DEVTNR1MPUD0(229398),      --Main Processing Unit D(Including 1*2G Memory and 2*1G CF Card)
					virentPTN6900DEVTNR1MPUB4(229399),      --Main Processing Unit B4(Including 1*2G Memory and 2*1G CF Card)
					virentPTN6900DEVTNR1SRU100A6(229400),   --Switch and Route Processing Unit A6(Including 1*2G Memory and 2*1G CF Card)
					virentPTN6900DEVTNR1SFU100C0(229401),   --100Gbps Switch Fabric Unit C(SFUI-100-C)
					virentPTN6900DEVTNR1SFU100B0(229402),   --100Gbps Switch Fabric Unit B(SFUI-100-B)
					virentPTN6900DEVTNR1MPUG0(229403),    --Main Processing Unit G(Including 1*1G CF Card)
					virentPTN6900DEVTNR1NPUI20(229404),    --Network Processing Unit Integrated with 2-Port 10GBase LAN/WAN-XFP
					virentPTN6900DEVTNRD0MPUD270(229450),    --for V600R006C00 TNRD0MPUD270(SBOM),Main Processing Unit D2

					--for V6R6 PTN6900 packing board
					virentPTN6900DEVTNRDMEPF0600(229423),    --Multi-Protocol Ethernet Processing Flexible Card Unit-06
					virentPTN6900DEVTNRDMEPF5000(229424),    --Multi-Protocol Ethernet Processing Flexible Card Unit-50
					virentPTN6900DEVTNRDMEPFA000(229425),    --Multi-Protocol Ethernet Processing Flexible Card Unit-100
					virentPTN6900DEVTNRD000EX800(229427),    --8 Ports 10 Gigabit Ethernet Processing Board (Supporting 1588v2)
					virentPTN6900DEVTNRD00EG2400(229429),    --24 Ports FE/GE Ethernet Processing Board (Supporting 1588v2)
					virentPTN6900DEVTNRD000EX501(229436),    --5 Ports 10 Gigabit Ethernet Processing Board (Supporting 1588v2)
					virentPTN6900DEVTNRD00EG4800(229437),    --48 Ports FE/GE Ethernet Processing Board (Supporting 1588v2)
					virentPTN6900DEVTNRD00EXL200(229439),    --2 Ports 40 Gigabit Base-CFP Ethernet Processing board (Supporting 1588v2)
						virentPTN6900DEVTNRD00EX1001(229442),    --10 Ports 10 Gigabit Ethernet Processing Board (Supporting 1588v2)

					-- V6R7 PTN packing 2012-10-11 begin
					virentPTN6900DEVTNRDMEPFA200(229443),    --for V600R007C00 TNRDMEPFA200(SBOM),Multi-Protocol Ethernet Processing Flexible Card Unit-120
					virentPTN6900DEVTNRDMEPFB400(229444),    --for V600R007C00 TNRDMEPFB400(SBOM),Multi-Protocol Ethernet Processing Flexible Card Unit-240
					virentPTN6900DEVTNRD00EX1201(229445),    --for V600R007C00 TNRD00EX1201(SBOM),12 Ports 10 Gigabit Ethernet Processing Board (Supporting 1588v2)
					virentPTN6900DEVTNRD00EXL201(229446),    --for V600R007C00 TNRD00EXL201(SBOM),2 Ports 40 Gigabit Base-CFP Ethernet Processing board (Supporting 1588v2)
					virentPTN6900DEVTNRD000EH100(229447),    --for V600R007C00 TNRD000EH100(SBOM),1 Ports 100GBase-CFP Ethernet Processing Board (Supporting 1588v2)
					virentPTN6900DEVTNRD00EX2400(229448),    --for V600R007C00 TNRD00EX2400(SBOM),24 Ports 10 Gigabit Ethernet Processing Board (Supporting 1588v2)
					virentPTN6900DEVTNRD000EH200(229449),    --for V600R007C00 TNRD000EH200(SBOM),2 Ports 100GBase-CFP Ethernet Processing Board (Supporting 1588v2)
					-- V6R7 PTN packing 2012-10-11 end

					--PTN7900 2013-8-8 by lishaobin begin
					virentPTN7900VPICTPA1EX12(229450),   --VPICTPA1EX12,12ch 10 Gigabit Ethernet Switching Processing Board-1*1
					virentPTN7900VPICTPA1EG24(229451),   --VPICTPA1EG24,24-Port Gigabit Ethernet Processing Board,1*1
					virentPTN7900VPICTPA1EXL2(229452),   --VPICTPA1EXL2,2ch 40 Gigabit Ethernet Switching Processing Board,1*1
					virentPTN7900VPICTPA1EH1(229453),    --VPICTPA1EH1,1 Ports 100GE Ethernet Processing Board
					virentPTN7900VPICTPA1EX8(229454),    --VPICTPA1EX8,8ch 10 Gigabit Ethernet Switching Processing Board-1*1
					virentPTN7900VPICTPA1CH1(229455),    --VPICTPA1CH1,16 Channels STM-1 CES Optical Interface board ,1*1
					virentPTN7900VPICTPA1CQ4(229456),    --VPICTPA1CQ4,4 Channels STM-4 CES Optical Interface board ,1*1
					virentPTN7900EfiRelay(229457),       --EfiRelay
					virentPTN7900EfiSwitch(229458),      --EfiSwitch
					-- FOR package board
					virentPTN7900VPICTPA1EX4(229459),   --VPICTPA1EX4,4ch 10 Gigabit Ethernet Switching Processing Board-1*1
					virentPTN7900VPICTPA1EXL1(229460),  --VPICTPA1EXL1,1ch 40 Gigabit Ethernet Switching Processing Board,1*1
					virentPTN7900VPICTPA1CO1(229461),   --VPICTPA1CO1,8ch Channels STM-1 CES Optical Interface board ,1*1
					virentPTN7900VPICTPA1EG16(229462),  --VPICTPA1EG16, 16-Port Gigabit Ethernet Processing Board,1*1
					virentPTN7900TPB1VXCS(229463),      --TPB1VXCS, Switch Fabric Unit Board,1*1
					--PTN7900 2013-8-8 by lishaobin end
					-- FOR PTN POTN&100G 80KM
					virentPTN7900VPICTPA1EH1A(229464),   --VPICTPA1EH1A,1-port WAN 80km 100 Gigabit Ethernet Switching Processing Board,1*1
					virentPTN7900VPICTPA1UH1(229465),    --VPICTPA1UH1,1-port 100 Gigabit Ethernet and OTN Hybrid Line Card,1*1
					virentPTN7900VPICTPA1UX10(229466),   --VPICTPA1UX10,10-port 10 Gigabit Ethernet and OTN Hybrid Line Card,1*1
					virentPTN7900VPICTPA1UH1A(229467),   --VPICTPA1UH1A,1-port 100 Gigabit Ethernet and OTN PIC Hybrid Line Card,1*1
					virentPTN7900VPICTPA1TG30(229468),   --VPICTPA1TG30,30-port 1 Gigabit Ethernet OTN Tributary Card,1*1
					virentPTN7900VPICTPA1TX10(229469),   --VPICTPA1TX10,10-port 10 Gigabit Ethernet OTN Tributary Card,1*1
					--PTN7900 2014-3-14 by zhangyi end
					--BEGIN: for PTN6900 V6R8C10 by w00195304
					virentPTN6900DEVTNRD00EXL600(229470),    --for V600R008C10 TNRD00EXL600(SBOM),6 Ports 40 Gigabit Ethernet Processing board (Supporting 1588v2)
					--END: for PTN6900 V6R8C10 by w00195304
					virentPTN6900DEVTNRD00SNCA70(229471),    --for V600R008C10 TNRD00SNCA70(SBOM),SNC Service Flexible Card Unit A(SNC-A)

-- NE20E-X6:
					virentNE20EX6LPUF10(675840),          --Flexible Card Line Processing Unit(NE20E LPUF-10,four slots)
					virentNE20EX6LPUF20(675841),          --Flexible Card Line Processing Unit(NE20E LPUF-20,2 sub-slots)
					virentNE20EX6LPUS(675842) ,           --40-Port 10/100/1000Base-RJ45 Line Processing Unit S(NE20E LPUS-20)
					virentNE20EX6SPU10(675843),           --Versatile Service Process Unit
					virentNE20EX6VSUI20A(675844),         --Integrated Versatile Service Unit(VSUI-20-A)
					virentNE20EX6MPUD0(675845),           --Main Processing Unit(Including 1*2G Memory and 1*1G CF Card)
					virentNE20EX6CR21EKFEB(675846),       --NE20E-X6 40-Port 10/100Base-RJ45 Line Processing Unit
					virentNE20EX6CR21LPUFC1(675847),      --NE20E-X6 FIC Service Processing Engine(NE20E-X6,four slots), 03053808 xiaoshouhe fen pei SBOM CR2DLPUF1000
					virentNE20EX6MPUH0(675848),            --NE20E-X6-NEW Main Processing Unit (Including 1*2G Memory )
					-- add NE20E for CX600 X1/X2  2012-09-17
					virentNE20ECR2D00MPUE10(675849),       --Main Processing Unit E
					virentNE20ECR2D0NSP5010(675850),       --Network Service Processor -50 (NSP-50)
					virentNE20ECR2DNSPE5010(675851),       --Network Service Processor -50-E (NSP-50-E, Apply for - 40~ 65 degree centigrade scene)
					virentNE20ECR2D00L2XF11(675852),       --2-Port 10GBase LAN/WAN-SFP+  Physical Interface Card
					virentNE20ECR2D00E8GF11(675853),          --8-Port 100/1000Base-X-SFP Physical Interface Card
					virentNE20ECR2D00E8GE11(675854),          --8-Port 10/100/1000Base-RJ45 Physical Interface Card
					virentNE20ECR2D00C4CF11(675855),          --4-Port Channelized OC-3c/STM-1c POS-SFP  Physical Interface Card
					virentNE20ECR2D000IE111(675856),          --32-Port E1 Physical Interface Card(120ohm)
					virentNE20ECR2D000IE110(675857),       --32-Port E1 Physical Interface Card(75ohm)
					virentNE20ECR2DNSP12010(675858),       --Network Service Processor -120 (NSP-120)
					virentNE20ECR2DNSP1201E(675859),        --Network Service Processor -120-E (NSP-120-E)
					virentNE20EX6VSUI20B(675860),          --Integrated Versatile Service Unit(VSUI-20-B)
				  virent8090DEVCR2DNSPB0010(675861),    -- V8R7 for SBOM ,CR2DNSPB0010, Network Service Processor(NSP-B)
				  virent8090DEVCR2DNSPA0010(675862),    -- V8R7 for SBOM ,CR2DNSPA0010, Network Service Processor(NSP-A)
				  virent8090DEVCR5DNPU24070(675863),    -- V8R7 for SBOM ,CR5DNPU24070, Network Processing Unit (NPU-240), NE40E
				  virent8090DEVCR5DNPU24071(675864)     -- V8R7 for SBOM ,CR5DNPU24071, Network Processing Unit (NPU-240), NE40E
					 }

		  HWAdditionalEntityType ::= TEXTUAL-CONVENTION
				STATUS current
				DESCRIPTION
					 "To show the relevant additional entity type in vender type object.
					 "
				SYNTAX INTEGER
					 {
					 other(1),                      -- none of the following
-- MA5200:
					 addentnameMA5200TCAM(135168),       -- TCAM  Module
					 addentnameMA5200CPCD(135169),       -- CPCD  Module
-- 8090:
					 addentname8090DEVFAD(561152),       -- FAD  Module
					 addentname8090DEVTCAM(561153),      -- TCAM Module
					 addentname8090DEVCLK(561154),       -- Clock Board
					 addentname8090DEVMIF(561155),        -- MIF Module
					 addentname8090DEVCR52CLKB(561156),  -- 1588 v2 Clock Board

-- ME60:
					 addentnameME60DEVFAD(159744),       -- FAD  Module
					 addentnameME60DEVTCAM(159745),      -- TCAM Module
					 addentnameME60DEVCLK(159746),       -- Clock Board
					 addentnameME60DEVMIF(159747),        -- MIF Module

-- CloudEngine: 0x000A8000~0x000A8fff(688128~692223)
					 addentnameCMU(688128)                -- CMU  Module
					 }



-- node define

		  ifAdminStatus OBJECT-TYPE
				SYNTAX INTEGER
					 {
					 up(1),
					 down(2),
					 testing(3),
-- huawei expand
					 block(65536),               -- Blocking operation
					 unblock(65537),             -- Unblocking operation
					 reset(65538),               -- Reset
					 localloopback(65539),       -- Local loopback
					 remoteloopback(65540),      -- Remote loopback
					 payloadloopback(65541),     -- Payload loopback
					 unloopback(65542),          -- Canceling loopback
					 linkrxblock(65543),         -- Blocking the Rx on a link
					 linktxblock(65544),         -- Blocking the Tx on a link
					 linkallblock(65545),        -- Blocking both the Rx and Tx on a link
					 linkrxunblock(65546),       -- Unblocking the Rx on a link
					 linktxunblock(65547),       -- Unblocking the Tx on a link
					 linkallunblock(65548),      -- Unblocking both the Rx and Tx on a link
					 adslloopbackafe(65549),     -- AFE looback on an ADSL port
					 adslloopbackhybrid(65550)   -- HYBRID loopback on an ADSL port
					 }
				MAX-ACCESS read-write
				STATUS current
				DESCRIPTION
					 "The current operational state of the interface.  The
					 testing(3) state indicates that no operational packets
					 can be passed.  If ifAdminStatus is down(2) then
					 ifOperStatus should be down(2).  If ifAdminStatus is
					 changed to up(1) then ifOperStatus should change to
					 up(1) if the interface is ready to transmit and
					 receive network traffic; it should change to
					 dormant(5) if the interface is waiting for external
					 actions (such as a serial line waiting for an incoming
					 connection); it should remain in the down(2) state if
					 and only if there is a fault that prevents it from
					 going to the up(1) state; it should remain in the
					 notPresent(6) state if the interface has missing
					 (typically, hardware) components.

					 huawei mib expand from 65536 .

					 Because  management states in the standard MIB can't satisfy
					 the request of all kinds of the product ,
					 the extension is performed.
					 Options:
					 1. up(1)                           - indicates up operation
					 2. down(2)                         - indicates down operation
					 3. testing(3)                      - indicates testing operation
					 4. block(65536)                    - indicates blocking operation
					 5. unblock(65537)                  - indicates unblocking operation
					 6. reset(65538)                    - indicates reseting operation
					 7. localloopback(65539)            - indicates local looping back operation
					 8. remoteloopback(65540)           - indicates remote looping back operation
					 9. payloadloopback(65541)          - indicates Payload looping back operation
					 10.unloopback(65542)               - indicates Canceling loopback operation
					 11.linkrxblock(65543)              - indicates Blocking the Rx on a link
					 12.linktxblock(65544)              - indicates Blocking the Tx on a link
					 13.linkallblock(65545)             - indicates Blocking both the Rx and Tx on a link
					 14.linkrxunblock(65546)            - indicates Unblocking the Rx on a link
					 15.linktxunblock(65547)            - indicates Unblocking the Tx on a link
					 16.linkallunblock(65548)           - indicates Unblocking both the Rx and Tx on a link
					 17.adslloopbackafe(65549)          - indicates AFE looback operation on an ADSL port
					 18.adslloopbackhybrid(65550)       - indicates HYBRID loopback operation on an ADSL port
					 "
				::= { ifEntry 7 }

		  ifOperStatus OBJECT-TYPE
				SYNTAX INTEGER
					 {
					 up(1),
					 down(2),
					 testing(3),
					 unknown(4),
					 dormant(5),
					 notPresent(6),
					 lowerLayerDown(7),
					 activing(65536),
					 block(65537),
					 config(65538),
					 localloopback(65539),           -- Local loopback
					 remoteloopback(65540),          -- Remote loopback
					 payloadloopback(65541),         -- Payload loopback
					 blockandlocalloopback(65542),   -- Blocking and performing the local loopback
					 blockandremoteloopback(65543),  -- Blocking and performing the remote loopback
					 blockandpayloadloopback(65544), -- Blocking and performing the payload loopback
					 linkrxblock(65545),             -- Blocking the Rx on a link
					 linktxblock(65546),             -- Blocking the Tx on a link
					 linkallblock(65547),            -- Blocking both the Rx and Tx on a link
					 fault(65548),                   -- Fault
					 unconfig(65549),                -- Not configured
					 empty(65550),                   -- Empty
					 adslloopbackafe(65551),         -- AFE looback on an ADSL port
					 adslloopbackhybrid(65552)       -- HYBRID loopback on an ADSL port
					 }
				MAX-ACCESS read-only
				STATUS current
				DESCRIPTION
					 "The current operational state of the interface.  The
					  testing(3) state indicates that no operational packets
					  can be passed.  If ifAdminStatus is down(2) then
					  ifOperStatus should be down(2).  If ifAdminStatus is
					  changed to up(1) then ifOperStatus should change to
					  up(1) if the interface is ready to transmit and
					  receive network traffic; it should change to
					  dormant(5) if the interface is waiting for external
					  actions (such as a serial line waiting for an incoming
					  connection); it should remain in the down(2) state if
					  and only if there is a fault that prevents it from
					  going to the up(1) state; it should remain in the
					  notPresent(6) state if the interface has missing
					  (typically, hardware) components.

					  huawei mib expand from 65536 .

					  Because  management states in the standard MIB can't satisfy
					  the request of all kinds of the product ,
					  the extension is performed.

					  Options:
					  1. up(1)                               - indicates that the operation state is up
					  2. down(2)                             - indicates that the operation state is down
					  3. testing(3)                          - indicates that the operation state is testing
					  4. unknown(4)                          - indicates that the operation state is unknown
					  5. dormant(5)                          - indicates that the operation state is dormant
					  6. notPresent(6)                       - indicates that the operation state is notPresent
					  7. lowerLayerDown(7)                   - indicates that the operation state is lowerLayerDown
					  8. activing(65536)                     - indicates that the operation state is activing
					  9. block(65537)                        - indicates that the operation state is block
					  10.config(65538)                       - indicates that the operation state is config
					  11.localloopback(65539)                - indicates that the operation state is Local loopback
					  12.remoteloopback(65540)               - indicates that the operation state is Remote loopback
					  13.payloadloopback(65541)              - indicates that the operation state is Payload loopback
					  14.blockandlocalloopback(65542)        - indicates that the operation state is Blocking and performing the local loopback
					  15.blockandremoteloopback(65543)       - indicates that the operation state is Blocking and performing the remote loopback
					  16.blockandpayloadloopback(65544)      - indicates that the operation state is Blocking and performing the payload loopback
					  17.linkrxblock(65545)                  - indicates that the operation state is Blocking the Rx on a link
					  18.linktxblock(65546)                  - indicates that the operation state is Blocking the Tx on a link
					  19.linkallblock(65547)                 - indicates that the operation state is Blocking both the Rx and Tx on a link
					  20.fault(65548)                        - indicates that the operation state is fault
					  21.unconfig(65549)                     - indicates that the operation state is not configured
					  22.empty(65550)                        - indicates that the operation state is empty
					  23.adslloopbackafe(65551)              - indicates AFE looback on an ADSL port
					  24.adslloopbackhybrid(65552)           - indicates HYBRID loopback on an ADSL port
					 "
				::= { ifEntry 8 }
		  hwAlarmId OBJECT-TYPE
				SYNTAX Integer32
				MAX-ACCESS accessible-for-notify
				STATUS current
				DESCRIPTION
					 "The trap id only valids in the alarm trap Varible binding parameters .
					  "
				::= { huaweiTCMIB 1 }

		  hwAlarmTime OBJECT-TYPE
				SYNTAX DateAndTime
				MAX-ACCESS accessible-for-notify
				STATUS current
				DESCRIPTION
					 "The trap  time  only valids in the alarm trap Varible binding parameters .
					  "
				::= { huaweiTCMIB 2 }

		  hwAlarmSn OBJECT-TYPE
				SYNTAX Integer32
				MAX-ACCESS accessible-for-notify
				STATUS current
				DESCRIPTION
					 "The serial number  only valids in the alarm trap Varible binding parameters .
					  "
				::= { huaweiTCMIB 3 }

		  hwCauseId OBJECT-TYPE
				SYNTAX Integer32
				MAX-ACCESS accessible-for-notify
				STATUS current
				DESCRIPTION
					 "The cause for   sending  a trap .
					  "
				::= { huaweiTCMIB 4 }

		  hwTrapType OBJECT-TYPE
				SYNTAX INTEGER
				{
				eventAlarm(0),                  -- Event alarm
				faultAlarm(1),                  -- Fault alarm
				clearAlarm(2),                  -- Recovery alarm
				synAlarm(3),                    -- Synchronization alarm
				maitainTrap(10),                -- Maintenance trap
				topDiscovery(11),               -- Topology discovery trap
				debugTrap(12)                   -- Debugging trap
				}

				MAX-ACCESS accessible-for-notify
				STATUS current
				DESCRIPTION
					 "The trap type .
					 Options:
					 1.eventAlarm(0)                 - Event alarm
					 2.faultAlarm(1)                 - Fault alarm
					 3.clearAlarm(2)                 - Recovery alarm
					 4.synAlarm(3)                   - Synchronization alarm
					 5.maitainTrap(10)               - Maintenance trap
					 6.topDiscovery(11)              - Topology discovery trap
					 7.debugTrap(12)                 - Debugging trap
					 "
				::= { huaweiTCMIB 5 }

		  hwFrameTypeOid OBJECT-TYPE
				SYNTAX HWFrameType
				MAX-ACCESS read-only
				STATUS current
				DESCRIPTION
					 "the Frames definition only for Entity-Mib use"
				::= { huaweiTCMIB 11 }

		  hwSlotTypeOid OBJECT-TYPE
				SYNTAX HWPCBType
				MAX-ACCESS read-only
				STATUS current
				DESCRIPTION
					 "the slots definition only for Entity-Mib use"
				::= { huaweiTCMIB 12}

		  hwSubslotTypeOid OBJECT-TYPE
				SYNTAX HWSubPCBType
				MAX-ACCESS read-only
				STATUS current
				DESCRIPTION
					 "the sub slots  definition only for Entity-Mib use"
				::= { huaweiTCMIB 13}

		  hwPortTypeOid    OBJECT-TYPE
				SYNTAX HWPortType
				MAX-ACCESS read-only
				STATUS current
				DESCRIPTION
					 "the ports definition only for Entity-Mib use"
				::= { huaweiTCMIB 14}
		  hwVirtualEntityOid    OBJECT-TYPE
				SYNTAX HWVirtualEntityType
				MAX-ACCESS read-only
				STATUS current
				DESCRIPTION
					 "The virtual entity definition only for Entity-mib."
				::= { huaweiTCMIB 15}

		  hwAdditionalEntityOid    OBJECT-TYPE
				SYNTAX HWAdditionalEntityType
				MAX-ACCESS read-only
				STATUS current
				DESCRIPTION
					 "The additional entity definition only for Entity-mib."
				::= { huaweiTCMIB 16}

	 END
