-- extracted from draft-clark-avt-rtpmibv2-01.txt
-- at Wed Jul 21 06:22:31 2004

RTCPXR-MIB DEFINITIONS ::= BEGIN
IMPORTS
       Counter32, Counter64, Gauge32, mib-2, Integer32, IpAddress,
       MODULE-IDENTITY,
       OBJECT-TYPE, Unsigned32                     FROM SNMPv2-SMI
       OBJECT-GROUP, MODULE-COMPLIANCE             FROM SNMPv2-CONF
       InterfaceIndex                              FROM IF-MIB;

rtcpXrMIB MODULE-IDENTITY
    LAST-UPDATED "TBD"
    ORGANIZATION
        "IETF AVT Working Group"
	CONTACT-INFO "TBD"
        DESCRIPTION
        "The managed objects of RTCP XR systems. 
         Refer to RFC 3611, Real Time Control Protocol Extended
         Reports (RTCP XR) Section 4.7 VoIP Metrics"
   REVISION     "TBD"
   DESCRIPTION  "Initial version of this MIB.
                 Published as draft-clark-avt-rtpmibv2-01.txt."

::= { mib-2 1 }

--
-- OBJECTS
--
rtcpXrMIBObjects OBJECT IDENTIFIER ::= { rtcpXrMIB 1 }
rtcpXrConformance OBJECT IDENTIFIER ::= { rtcpXrMIB 2 }


--
-- RTCP Extended Reports - Voice over IP Metrics
--

rtcpXrVoipTable OBJECT-TYPE
    SYNTAX SEQUENCE OF RtcpXrVoipEntry
    ACCESS not-accessible
    STATUS mandatory
    DESCRIPTION
      "Table of information about a receiver or receivers of RTCP XR
       session data. RTP hosts that receive RTCP XR session packets
       MUST create an entry in this table for that receiver/sender
       pair.  RTP hosts that send RTCP XR session packets MAY create
       an entry in this table for each receiver to their stream
       using RTCP XR feedback from the RTP group. "
    ::= { rtcpXrMIBObjects 1 }

rtcpXrVoipEntry OBJECT-TYPE
    SYNTAX RtcpXrVoipEntry
    ACCESS not-accessible
    STATUS mandatory
    DESCRIPTION
        "An entry in the table of call records.  A row in this table 
         is created for each RTP session endpoint participating."
    INDEX { rtcpXrVoipIndex }
    ::= { rtcpXrVoipTable 1 }

RtcpXrVoipEntry ::= SEQUENCE {
    rtcpXrVoipIndex                          INTEGER,
    rtcpXrVoipCallIdentifier                 OCTET STRING,
    rtcpXrVoipSourceIPaddress                IpAddress,
    rtcpXrVoipSourcePort                     INTEGER,
    rtcpXrVoipVocoderType                    INTEGER,
    rtcpXrVoipCallDurationMs                 INTEGER,
    rtcpXrVoipNetworkLossRate                INTEGER,
    rtcpXrVoipAverageDiscardRate             INTEGER,
    rtcpXrVoipBurstLossDensity               INTEGER,
    rtcpXrVoipBurstLenMs                     INTEGER,
    rtcpXrVoipGapLossDensity                 INTEGER,
    rtcpXrVoipGapLenMs                       INTEGER,
    rtcpXrVoipAverageOneWayDelay             INTEGER,
    rtcpXrVoipEndSystemDelay                 INTEGER,
    rtcpXrVoipNoiseLeveldBm                  INTEGER,
    rtcpXrVoipSignalLeveldBm                 INTEGER,
    rtcpXrVoipLocalRERLdB                    INTEGER,
    rtcpXrVoipConversationalRCQ              INTEGER,
    rtcpXrVoipListeningMOSLQ                 INTEGER,
    rtcpXrVoipConversationalMOSCQ            INTEGER,
    rtcpXrVoipPlcType                        INTEGER,
    rtcpXrVoipJitterBufferAdaptationMode     INTEGER,                   
    rtcpXrVoipJitterBufferAdaptationRate     INTEGER,
    rtcpXrVoipJitterBufferAverageDelay       INTEGER,
    rtcpXrVoipJitterBufferMaximumDelay       INTEGER,
    rtcpXrVoipJitterBufferSize               INTEGER
}

rtcpXrVoipIndex OBJECT-TYPE
    SYNTAX INTEGER (0..65535)
    ACCESS read-only
    STATUS mandatory
    DESCRIPTION
        "Index for this call."
    ::= { rtcpXrVoipEntry 1 }

rtcpXrVoipCallIdentifier OBJECT-TYPE
    SYNTAX OCTET STRING
    ACCESS read-only
    STATUS mandatory
    DESCRIPTION
        "Call identifier for this call (= SDES?)." 
    ::= { rtcpXrVoipEntry 2 }

rtcpXrVoipSourceIPaddress OBJECT-TYPE
    SYNTAX IpAddress
    ACCESS read-only
    STATUS mandatory
    DESCRIPTION
        "Source IP address for this session."
    ::= { rtcpXrVoipEntry 3 }

rtcpXrVoipSourcePort OBJECT-TYPE
    SYNTAX INTEGER
    ACCESS read-only
    STATUS mandatory
    DESCRIPTION
        "Source UDP Port for this call."
    ::= { rtcpXrVoipEntry 4 }

rtcpXrVoipVocoderType OBJECT-TYPE
    SYNTAX INTEGER
    ACCESS read-only
    STATUS mandatory
    DESCRIPTION
        "Vocoder type used on this call."
    ::= { rtcpXrVoipEntry 5 }

rtcpXrVoipCallDurationMs OBJECT-TYPE
    SYNTAX INTEGER
    ACCESS read-only
    STATUS mandatory
    DESCRIPTION
        "Duration of call in milliseconds."
    ::= { rtcpXrVoipEntry 6 }

rtcpXrVoipNetworkLossRate OBJECT-TYPE
    SYNTAX INTEGER
    ACCESS read-only
    STATUS mandatory
    DESCRIPTION
        "Average rate of network packet loss (see RFC3611 Section 4.7)."
    ::= { rtcpXrVoipEntry 7 }

rtcpXrVoipAverageDiscardRate OBJECT-TYPE
    SYNTAX INTEGER
    ACCESS read-only
    STATUS mandatory
    DESCRIPTION
        "Average rate of discards due to jitter(see RFC3611 Section 4.7)."
    ::= { rtcpXrVoipEntry 8 }

rtcpXrVoipBurstLossDensity OBJECT-TYPE
    SYNTAX INTEGER
    ACCESS read-only
    STATUS mandatory
    DESCRIPTION
        "Density of loss and discarded packets during burst periods.
         (see RFC3611 Section 4.7)"
    ::= { rtcpXrVoipEntry 9 }

rtcpXrVoipBurstLenMs OBJECT-TYPE
    SYNTAX INTEGER
    ACCESS read-only
    STATUS mandatory
    DESCRIPTION
        "Average length of bursts in milliseconds (see RFC3611 Section 4.7)."
    ::= { rtcpXrVoipEntry 10 }

rtcpXrVoipGapLossDensity OBJECT-TYPE
    SYNTAX INTEGER
    ACCESS read-only
    STATUS mandatory
    DESCRIPTION
        "Density of loss and discarded packets during gap periods
         (see RFC3611 Section 4.7)."
    ::= { rtcpXrVoipEntry 11 }

rtcpXrVoipGapLenMs OBJECT-TYPE
    SYNTAX INTEGER
    ACCESS read-only
    STATUS mandatory
    DESCRIPTION
        "Average length of gaps in milliseconds (see RFC3611 Section 4.7)."
    ::= { rtcpXrVoipEntry 12 }

rtcpXrVoipAverageOneWayDelay OBJECT-TYPE
    SYNTAX INTEGER
    ACCESS read-only
    STATUS mandatory
    DESCRIPTION
        "Average (symmetric) one way RTCP delay on call. A value of zero may 
         indicate that this value has not yet been determined.
         (see RFC3611 Section 4.7)."
    ::= { rtcpXrVoipEntry 13 }

rtcpXrVoipEndSystemDelay OBJECT-TYPE
    SYNTAX INTEGER
    ACCESS read-only
    STATUS mandatory
    DESCRIPTION
        "Average end system delay on call. A value of zero may 
         indicate that this value has not yet been determined
         (see RFC3611 Section 4.7)."
    ::= { rtcpXrVoipEntry 14 }

rtcpXrVoipNoiseLeveldBm OBJECT-TYPE
    SYNTAX INTEGER
    ACCESS read-only 
    STATUS mandatory
    DESCRIPTION
        "Measured received silent period noise level in dBm
         (see RFC3611 Section 4.7)."
    ::= { rtcpXrVoipEntry 15 }

rtcpXrVoipSignalLeveldBm OBJECT-TYPE
    SYNTAX INTEGER
    ACCESS read-only
    STATUS mandatory
    DESCRIPTION
        "Measured received signal level during talkspurts in dBm
        (see RFC3611 Section 4.7)."
    ::= { rtcpXrVoipEntry 16 }

rtcpXrVoipLocalRERLdB OBJECT-TYPE
    SYNTAX INTEGER
    ACCESS read-only
    STATUS mandatory
    DESCRIPTION
        "Residual Echo Return Loss measured at this endpoint
         (see RFC3611 Section 4.7)."
    ::= { rtcpXrVoipEntry 17 }

rtcpXrVoipConversationalRCQ OBJECT-TYPE
    SYNTAX INTEGER
    ACCESS read-only
    STATUS mandatory
    DESCRIPTION
        "Conversational quality R factor for this call
         (see RFC3611 Section 4.7)."
    ::= { rtcpXrVoipEntry 18 }

rtcpXrVoipListeningMOSLQ OBJECT-TYPE
    SYNTAX INTEGER
    ACCESS read-only
    STATUS mandatory
    DESCRIPTION
        "Estimated listening quality MOS for this call
         (see RFC3611 Section 4.7)."
    ::= { rtcpXrVoipEntry 19 }

rtcpXrVoipConversationalMOSCQ OBJECT-TYPE
    SYNTAX INTEGER
    ACCESS read-only
    STATUS mandatory
    DESCRIPTION
        "Estimated conversational quality MOS for this call
         (see RFC3611 Section 4.7)."
    ::= { rtcpXrVoipEntry 20 }

rtcpXrVoipPlcType OBJECT-TYPE
    SYNTAX INTEGER { disabled(1),
                     enhanced(2), 
                     standard(3),
                     unspecified (4)}
    ACCESS read-only
    STATUS mandatory
    DESCRIPTION
        "Defines type of packet loss concealment used on this call
         (see RFC3611 Section 4.7)."
    ::= { rtcpXrVoipEntry 21 }

rtcpXrVoipJitterBufferAdaptationMode OBJECT-TYPE
    SYNTAX INTEGER { reserved (1),
                     nonAdaptive (2),
                     adaptive (3),
                     unknown (4) }
    ACCESS read-only
    STATUS mandatory
    DESCRIPTION
        "Defines if jitter buffer is in fixed or adaptive mode
         (see RFC3611 Section 4.7)."
    ::= { rtcpXrVoipEntry 22 }

rtcpXrVoipJitterBufferAdaptationRate OBJECT-TYPE
    SYNTAX INTEGER 
    ACCESS read-only
    STATUS mandatory
    DESCRIPTION
        "Estimated adaptation rate of jitter buffer
         (see RFC3611 Section 4.7)."
    ::= { rtcpXrVoipEntry 23 }

rtcpXrVoipJitterBufferAverageDelay OBJECT-TYPE
    SYNTAX INTEGER 
    ACCESS read-only
    STATUS mandatory
    DESCRIPTION
        "Average size of jitter buffer in mS
         (see RFC3611 Section 4.7)."
    ::= { rtcpXrVoipEntry 24 }

rtcpXrVoipJitterBufferMaximumDelay OBJECT-TYPE
    SYNTAX INTEGER 
    ACCESS read-only
    STATUS mandatory
    DESCRIPTION
        "Maximum delay through jitter buffer at current size in mS
         (see RFC3611 Section 4.7)."
    ::= { rtcpXrVoipEntry 25 }

rtcpXrVoipJitterBufferSize OBJECT-TYPE
    SYNTAX INTEGER 
    ACCESS read-only
    STATUS mandatory
    DESCRIPTION
        "Absolute maximum size jitter buffer can reach in mS
         (see RFC3611 Section 4.7)."
    ::= { rtcpXrVoipEntry 26 }

END

-- 
--    Copyright (C) The Internet Society (2004).  This document is subject
--    to the rights, licenses and restrictions contained in BCP 78, and
--    except as set forth therein, the authors retain all their rights
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
